module open-traffic-generator-ospfv3 {
  yang-version "1";

  namespace "http://gitub.com/open-traffic-generator/models-yang/models/ospfv3";
  prefix "otg-ospfv3";

  import open-traffic-generator-types {
    prefix "otg-types";
  }

  organization
    "OpenTrafficGenerator working group";

  contact
    "OpenTrafficGenerator working group
     opentrafficgenerator@googlegroups.com";

  description
    "This module defines telemetry that relates to OSPFv3 sessions that
    are controlled by an open traffic generator (OTG) whose definition
    is outside of the context of this module.";

  revision 2022-01-21 {
    description "Initial revision.";
    reference "0.1.0";
  }

  grouping ospfv3-top {
    description
      "Top-level structural grouping for OSPFv3 router telemetry
      entries.";

    container ospfv3-routers {
      description
        "OSPFv3 router telemetry collected by the OTG device.";

      list ospfv3-router {
        key "name";

        config false;

        description
          "Each OSPFv3 router is identified by an arbitrary string
          identifier.";

        leaf name {
          type leafref {
            path "../state/name";
          }
          description
            "Reference to the OSPFv3 router's name, acting as a key of
            the OSPFv3 router list.";
        }

        container state {
          description
            "Operational state of an individual OSPFv3 router.";

          uses ospfv3-state;
        }
      }
    }
  }

  grouping ospfv3-state {
    description
      "Operational state of an individual OSPFv3 router.";

    leaf name {
      type string;
      description
        "An arbitrary name of the OSPFv3 router determined by
        the OTG configuration.";
    }

    container counters {
      description
        "Counters of an individual OSPFv3 router.";

      uses ospfv3-counters;
    }

    container link-state-database {
      description
        "This sub-module describes a YANG model for the OSPF Link State
        Database (LSDB).";

      uses lsa-states;
    }
  }

  grouping lsa-states {
    description
      "This grouping defines OSPFv3 LSA state information.";

    reference
      "1. https://github.com/openconfig/public/tree/master/release/models/ospf";

    container lsa-states {
      description
        "Container of OSPFv3 LSA state information.";

      list router-lsa {
        key "link-state-id";
        description
          "Contents of the router LSA.";

        leaf link-state-id {
          type leafref {
            path "../state/link-state-id";
          }
          description
            "Reference to the Link State ID of the neighbor.";
        }

        container state {
          description
            "State parameters of router LSA.";

          uses ospfv3-lsdb-lsa-state;

          leaf neighbor-router {
            type otg-types:ipv4-address;
            description
              "The router ID of the neighbor that is attached to the link.";
          }

          list link {
            description
              "OSPFv3 link attributes.";

            uses ospfv3-lsdb-link-state;
          }
        }
      }

      list network-lsa {
        key "link-state-id";
        description
          "Contents of the network LSA.";

        leaf link-state-id {
          type leafref {
            path "../state/link-state-id";
          }
          description
            "Reference to the Link State ID of the neighbor.";
        }

        container state {
          description
            "State parameters of network LSA.";

          uses ospfv3-lsdb-lsa-state;

          leaf-list attached-router {
            type otg-types:ipv4-address;
            description
              "A list of the router ID of the routers that are attached to
              the network described by the Network LSA.";
          }
        }
      }

      list inter-area-prefix-lsa {
        key "link-state-id";
        description
          "Contents of the Inter-Area-Prefix LSA.";

        leaf link-state-id {
          type leafref {
            path "../state/link-state-id";
          }
          description
            "Reference to the Link State ID of the neighbor.";
        }

        container state {
          description
            "State parameters of inter-area-prefix LSA.";

          uses ospfv3-lsdb-lsa-state;

          leaf prefix-length {
            type uint32;
            description
              "The length of the IPv6 address prefix, in bits.";
          }

          leaf metric {
            type uint32;
            description
              "The cost of the summary route TOS level 0 and all
              unspecified levels.";
          }

          leaf address-prefix {
            type otg-types:ipv6-address;
            description
              "The first IPv6 address prefix to be advertised in the LSA.";
          }
        }
      }

      list inter-area-router-lsa {
        key "link-state-id";
        description
          "Contents of the Inter-Area-Router LSA.";

        leaf link-state-id {
          type leafref {
            path "../state/link-state-id";
          }
          description
            "Reference to the Link State ID of the neighbor.";
        }

        container state {
          description
            "State parameters of inter-area-router LSA.";

          uses ospfv3-lsdb-lsa-state;

          leaf metric {
            type uint32;
            description
              "The cost of the summary route TOS level 0 and all
              unspecified levels.";
          }

          leaf destination_router {
            type otg-types:ipv4-address;
            description
              "The destination router of LSA.";
          }
        }
      }

      list external-as-lsa {
        key "link-state-id";
        description
          "Contents of the AS External LSA.";

        leaf link-state-id {
          type leafref {
            path "../state/link-state-id";
          }
          description
            "Reference to the Link State ID of the neighbor.";
        }

        container state {
          description
            "State parameters of external as LSA.";

          uses ospfv3-lsdb-lsa-state;

          leaf address-prefix {
            type otg-types:ipv6-address;
            description
              "The first IPv6 address prefix to be advertised in the LSA.";
          }

          leaf prefix-length {
            type uint32;
            description
              "The length of the IPv6 address prefix, in bits.";
          }

          leaf metric {
            type uint32;
            description
              "The cost of the summary route TOS level 0 and all
              unspecified levels.";
          }

          leaf referenced-ls-type {
            type uint32;
            description
              "The type of the LS referenced in this LSA.";
          }

          leaf forwarding-address {
            type otg-types:ipv6-address;
            description
              "The IPV6 address where traffic for the advertised destination is forwarded.";
          }

          leaf route-tag {
            type otg-types:ipv4-address;
            description
              "The optional field may be used to communicate additional information between AS boundary routers.";
          }
        }
      }

      list nssa-lsa {
        key "link-state-id";
        description
          "Contents of the NSSA LSA.";

        leaf link-state-id {
          type leafref {
            path "../state/link-state-id";
          }
          description
            "Reference to the Link State ID of the neighbor.";
        }

        container state {
          description
            "State parameters of nssa LSA.";

          uses ospfv3-lsdb-lsa-state;

          leaf address-prefix {
            type otg-types:ipv6-address;
            description
              "The first IPv6 address prefix to be advertised in the LSA.";
          }

          leaf prefix-length {
            type uint32;
            description
              "The length of the IPv6 address prefix, in bits.";
          }

          leaf metric {
            type uint32;
            description
              "The cost of the summary route TOS level 0 and all
              unspecified levels.";
          }

          leaf forwarding-address {
            type otg-types:ipv6-address;
            description
              "The IPV6 address where traffic for the advertised destination is forwarded.";
          }

          leaf route-tag {
            type otg-types:ipv4-address;
            description
              "The optional field may be used to communicate additional information between AS boundary routers.";
          }
        }
      }

      list link-lsa {
        key "link-state-id";
        description
          "Contents of the Link LSA.";

        leaf link-state-id {
          type leafref {
            path "../state/link-state-id";
          }
          description
            "Reference to the Link State ID of the neighbor.";
        }

        container state {
          description
            "State parameters of link LSA.";

          uses ospfv3-lsdb-lsa-state;

          leaf address-prefix {
            type otg-types:ipv6-address;
            description
              "The first IPv6 address prefix to be advertised in the LSA.";
          }

          leaf prefix-length {
            type uint32;
            description
              "The length of the IPv6 address prefix, in bits.";
          }

          leaf link-local-address {
            type otg-types:ipv6-address;
            description
              "The IPV6 Link Local address for the originating router's interface attached to this link.";
          }
        }
      }

      list intra-area-prefix-lsa {
        key "link-state-id";
        description
          "Contents of the Intra-Area-Prefix LSA.";

        leaf link-state-id {
          type leafref {
            path "../state/link-state-id";
          }
          description
            "Reference to the Link State ID of the neighbor.";
        }

        container state {
          description
            "State parameters of intra area prefix LSA.";

          uses ospfv3-lsdb-lsa-state;

          leaf address-prefix {
            type otg-types:ipv6-address;
            description
              "The first IPv6 address prefix to be advertised in the LSA.";
          }

          leaf prefix-length {
            type uint32;
            description
              "The length of the IPv6 address prefix, in bits.";
          }

          leaf metric {
            type uint32;
            description
              "The cost of the summary route TOS level 0 and all
              unspecified levels.";
          }
        }
      }
    }
  }

  grouping ospfv3-counters {
    description
      "Level counters of the OSPFv3 router.";

    leaf sessions-up {
      type otg-types:counter64;
      description
        "The total number of sessions that are fully up.";
    }

    leaf sessions-down {
      type otg-types:counter64;
      description
        "The total number of sessions that are down.";
    }

    leaf sessions-flap {
      type otg-types:counter64;
      description
        "The total number of sessions flap.";
    }

    leaf out-hellos {
      type otg-types:counter64;
      description
        "The total number of HELLO messages sent.";
    }

    leaf in-hellos {
      type otg-types:counter64;
      description
        "The total number of HELLO messages received.";
    }

    leaf out-dbds {
      type otg-types:counter64;
      description
        "The total number of DBD messages sent.";
    }

    leaf in-dbds {
      type otg-types:counter64;
      description
        "The total number of DBD messages received.";
    }

    leaf out-ls-requests {
      type otg-types:counter64;
      description
        "The total number of LS Request messages sent.";
    }

    leaf in-ls-requests {
      type otg-types:counter64;
      description
        "The total number of LS Request messages received.";
    }

    leaf out-ls-updates {
      type otg-types:counter64;
      description
        "The total number of LS Update messages sent.";
    }

    leaf in-ls-updates {
      type otg-types:counter64;
      description
        "The total number of LS Update messages received.";
    }

    leaf out-ls-acks {
      type otg-types:counter64;
      description
        "The total number of LS Ack messages sent.";
    }

    leaf in-ls-acks {
      type otg-types:counter64;
      description
        "The total number of LS Ack messages received.";
    }

    leaf out-lsas {
      type otg-types:counter64;
      description
        "The total number of link state protocol data units (LSAs) sent.";
    }

    leaf in-lsas {
      type otg-types:counter64;
      description
        "The total number of link state protocol data units (LSAs) received.";
    }

    leaf out-router-lsas {
      type otg-types:counter64;
      description
        "The total number of OSPFv3 Router (Type 1) LSAs sent.";
    }

    leaf in-router-lsas {
      type otg-types:counter64;
      description
        "The total number of OSPFv3 Router (Type 1) LSAs received.";
    }

    leaf out-network-lsas {
      type otg-types:counter64;
      description
        "The total number of OSPFv3 Network (Type 2) LSAs sent.";
    }

    leaf in-network-lsas {
      type otg-types:counter64;
      description
        "The total number of OSPFv3 Network (Type 2) LSAs received.";
    }

    leaf out-inter-area-prefix-lsas {
      type otg-types:counter64;
      description
        "The total number of OSPFv3 Inter-Area-Prefix (Type 3) LSAs sent.";
    }

    leaf in-inter-area-prefix-lsas {
      type otg-types:counter64;
      description
        "The total number of OSPFv3 Inter-Area-Prefix (Type 3) LSAs received.";
    }

    leaf out-inter-area-router-lsas {
      type otg-types:counter64;
      description
        "The total number of OSPFv3 Inter-Area-Router (Type 4) LSAs sent.";
    }

    leaf in-inter-area-router-lsas {
      type otg-types:counter64;
      description
        "The total number of OSPFv3 Inter-Area-Router (Type 4) LSAs received.";
    }

    leaf out-external-lsas {
      type otg-types:counter64;
      description
        "The total number of OSPFv3 External (Type 5) LSAs sent.";
    }

    leaf in-external-lsas {
      type otg-types:counter64;
      description
        "The total number of OSPFv3 External (Type 5) LSAs received.";
    }

    leaf out-nssa-lsas {
      type otg-types:counter64;
      description
        "The total number of OSPFv3 NSSA (Type 7) LSAs sent.";
    }

    leaf in-nssa-lsas {
      type otg-types:counter64;
      description
        "The total number of OSPFv3 NSSA (Type 7) LSAs received.";
    }

    leaf out-link-lsas {
      type otg-types:counter64;
      description
        "The total number of OSPFv3 Link (Type 8) LSAs sent.";
    }

    leaf in-link-lsas {
      type otg-types:counter64;
      description
        "The total number of OSPFv3 Link (Type 8) LSAs received.";
    }

    leaf out-intra-area-prefix-lsas {
      type otg-types:counter64;
      description
        "The total number of OSPFv3 Intra-Area-Prefix (Type 9) LSAs sent.";
    }

    leaf in-intra-area-prefix-lsas {
      type otg-types:counter64;
      description
        "The total number of OSPFv3 Intra-Area-Prefix (Type 9) LSAs received.";
    }
  }

  grouping ospfv3-lsdb-lsa-state {
    description
      "Generic parameters of an OSPFv3 LSA.";

    leaf link-state-id {
      type otg-types:ipv4-address;
      description
        "The Link State ID for the specified LSA type.";
    }

    leaf advertising-router {
      type otg-types:ipv4-address;
      description
        "The router ID of the router that originated the LSA.";
    }

    leaf sequence-number {
      type uint32;
      description
        "Sequence number to detect old and duplicate LSAs.
         The greater the sequence number the more recent the LSA.";
    }

    leaf age {
      type uint16;
      description
        "The time since the LSA's generation in seconds.";
    }
  }

  grouping ospfv3-lsdb-link-state {
    description
      "Generic attributes used to identify link within OSPFv3.";

    leaf type {
      type enumeration {
        enum POINT_TO_POINT {
          description
            "The LSA represents a point-to-point connection to another
            router.";
        }
        enum TRANSIT {
          description
            "The LSA represents a connection to a transit network.";
        }
        enum STUB {
          description
            "The LSA represents a connection to a stub network.";
        }
        enum VIRTUAL {
          description
            "The LSA represents a virtual link connection.";
        }
      }
      description
        "The data associated with the link type.
        The value is dependent upon the subtype of the LSA.";
    }

    leaf metric {
      type uint16;
      description
        "The cost of utilising the link specified independent of TOS.";
    }
  }

  uses ospfv3-top;
}
