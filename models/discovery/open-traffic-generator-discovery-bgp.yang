submodule open-traffic-generator-discovery-bgp {
  yang-version "1";

  belongs-to "open-traffic-generator-discovery" {
    prefix "otg-disc";
  }

  import open-traffic-generator-types {
    prefix "otg-types";
  }

  organization
    "OpenTrafficGenerator working group";

  contact
    "OpenTrafficGenerator working group
     opentrafficgenerator@googlegroups.com";

  description
    "This module defines telemetry that relates to BGP peers defined
    by an open traffic generator (OTG) whose definition is at
    http://github.com/open-traffic-generator/models.";

  revision 2022-01-21 {
    description
      "Initial revision";
    reference "0.1.0";
  }

  grouping bgp-top {
    description
      "Top-level structural grouping for OTG BGP entries.";

    container bgp-peers {
      description
        "BGP peers defined by an OTG.";

      list bgp-peer {
        key "name";

        config false;

        description
          "An individual BGP peer defined by an OTG.";

        leaf name {
          type leafref {
            path "../state/name";
          }
          description
            "Reference to an BGP peer's name, acting as a key of
            the bgp-peers list.";
        }

        container state {
          description
            "Operational state of an individual BGP peer.";

          leaf name {
            type string;
            description
              "An arbitary name of an OTG BGP peer determined by the OTG
              configuration.";
          }
        }

        container unicast-ipv4-prefixes {
          description
            "Discovered unicast IPv4 prefixes of a BGP peer";

          list unicast-ipv4-prefix {
            key "address prefix-length origin path-id";

            description
              "A list of BGP unicast IPv4 prefixes.";

            leaf address {
              type leafref {
                path "../state/address";
              }
              description
                "Reference to a unicast IPv4 address, acting as part
                of a key to the unicast-ipv4-prefix list.";
            }

            leaf prefix-length {
              type leafref {
                path "../state/prefix-length";
              }
              description
                "Reference to a prefix-length, acting as part of a
                key to the unicast-ipv4-prefix list.";
            }

            leaf origin {
              type leafref {
                path "../state/origin";
              }
              description
                "Reference to an origin, acting as part of a
                key to the unicast-ipv4-prefix list.";
            }

            leaf path-id {
              type leafref {
                path "../state/path-id";
              }
              description
                "Reference to a path-id, acting as part of a
                key to the unicast-ipv4-prefix list.";
            }

            container state {
              description
                "The container for unicast ipv4 prefix state.";

              leaf address {
                type otg-types:ipv4-address;
                description
                  "The IPv4 address.";
              }

              leaf prefix-length {
                type uint32;
                description
                  "The prefix length.";
              }

              leaf origin {
                type enumeration {
                  enum IGP {
                    description
                      "The origin is internal.";
                  }
                  enum EGP {
                    description
                      "The origin is external.";
                  }
                }
                description
                  "The origin of the prefix.";
              }

              leaf path-id {
                type uint32;
                description
                  "The path id.";
              }

              leaf next-hop-ipv4-address {
                type otg-types:ipv4-address;
                description
                  "The IPv4 address of the egress interface.";
              }

              leaf next-hop-ipv6-address {
                type otg-types:ipv6-address;
                description
                  "The IPv6 address of the egress interface.";
              }
            }
          }
        }

        container unicast-ipv6-prefixes {
          description
            "Discovered unicast IPv6 prefixes of a BGP peer";

          list unicast-ipv6-prefix {
            key "address prefix-length origin path-id";

            description
              "A list of BGP unicast IPv6 prefixes.";

            leaf address {
              type leafref {
                path "../state/address";
              }
              description
                "Reference to a unicast IPv6 address, acting as part
                of a key to the unicast-ipv6-prefix list.";
            }

            leaf prefix-length {
              type leafref {
                path "../state/prefix-length";
              }
              description
                "Reference to a prefix-length, acting as part of a
                key to the unicast-ipv6-prefix list.";
            }

            leaf origin {
              type leafref {
                path "../state/origin";
              }
              description
                "Reference to an origin, acting as part of a
                key to the unicast-ipv6-prefix list.";
            }

            leaf path-id {
              type leafref {
                path "../state/path-id";
              }
              description
                "Reference to a path-id, acting as part of a
                key to the unicast-ipv6-prefix list.";
            }

            container state {
              description
                "The container for unicast IPv6 prefix state.";

              leaf address {
                type otg-types:ipv6-address;
                description
                  "The IPv6 address.";
              }

              leaf prefix-length {
                type uint32;
                description
                  "The prefix length.";
              }

              leaf origin {
                type enumeration {
                  enum IGP {
                    description
                      "The origin is internal.";
                  }
                  enum EGP {
                    description
                      "The origin is external.";
                  }
                }
                description
                  "The origin of the prefix.";
              }

              leaf path-id {
                type uint32;
                description
                  "The path id.";
              }

              leaf next-hop-ipv4-address {
                type otg-types:ipv4-address;
                description
                  "The IPv4 address of the egress interface.";
              }

              leaf next-hop-ipv6-address {
                type otg-types:ipv6-address;
                description
                  "The IPv6 address of the egress interface.";
              }
            }
          }
        }
      }
    }
  }
}
