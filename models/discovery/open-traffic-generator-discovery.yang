module open-traffic-generator-discovery {
  yang-version "1";

  namespace "http://github.com/open-traffic-generator/models/yang/models/otg-disc";
  prefix "otg-disc";

  include open-traffic-generator-discovery-interfaces;

  organization
    "OpenTrafficGenerator working group";

  contact
    "OpenTrafficGenerator working group
     opentrafficgenerator@googlegroups.com";

  description
    "This module defines telemetry that relates to discovery defined
    by an open traffic generator (OTG) whose definition is at
    http://github.com/open-traffic-generator/models.";

  revision 2022-01-21 {
    description
      "Initial revision";
    reference "0.1.0";
  }

  uses interface-top;
}
