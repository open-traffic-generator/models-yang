module open-traffic-generator-bgp {
  yang-version "1";

  namespace "http://github.com/open-traffic-generator/models/yang/models/bgp";
  prefix "otg-bgp";

  import open-traffic-generator-types {
    prefix "otg-types";
  }

  organization
    "OpenTrafficGenerator working group";

  contact
    "OpenTrafficGenerator working group
     opentrafficgenerator@googlegroups.com";

  description
    "This module defines telemetry that relates to BGP sessions that
    are controlled by an open traffic generator (OTG) whose definition
    is outside of the context of this module.";

  revision 2022-01-21 {
    description "Initial revision.";
    reference "0.1.0";
  }

  grouping bgp-top {
    description
      "Top-level structural grouping for BGP session telemetry
      entries.";

    container bgp-peers {
      description
        "BGP peer session telemetry collected by the ATE device.";

      list bgp-peer {
        key "name";

        config false;

        description
          "Each BGP peer is identified by an arbitrary string
          identifier.";

        leaf name {
          type leafref {
            path "../state/name";
          }
          description
            "Reference to the BGP peer's name, acting as a key of the
            BGP peer list.";
        }

        container state {
          config false;

          description
            "Operational state of an individual BGP peer.";

          uses bgp-state;

          container counters {
            description
              "Counters of an individual BGP peer.";

            uses bgp-counters;
          }
        }

        uses bgp-ipv4-prefixes;

        uses bgp-ipv6-prefixes;

        uses mpls-ipv4-prefixes;

        uses mpls-ipv6-prefixes;

        uses mpls-vpn-ipv4-prefixes;

        uses mpls-vpn-ipv6-prefixes;
      }
    }
  }

  grouping bgp-state {
    description
      "Operational state of the individual BGP peer.";

    leaf name {
      type string;
      description
        "An arbitrary name of the BGP peer determined by the ATE
        configuration.";
    }

    leaf session-state {
      type enumeration {
          enum IDLE {
            description
              "Neighbor is down, and in the Idle state of the
              FSM";
          }
          enum CONNECT {
            description
              "Neighbor is down, and the session is waiting for
              the underlying transport session to be established";
          }
          enum ACTIVE {
            description
              "Neighbor is down, and the local system is awaiting
              a connection from the remote peer";
          }
          enum OPEN_SENT {
            description
              "Neighbor is in the process of being established.
              The local system has sent an OPEN message";
          }
          enum OPEN_CONFIRM {
            description
              "Neighbor is in the process of being established.
              The local system is awaiting a NOTIFICATION or
              KEEPALIVE message";
          }
          enum ESTABLISHED {
            description
              "Neighbor is up. The BGP session with the peer is
              established";
          }
        }
        description
          "Operational state of the BGP peer";
    }
  }

  grouping bgp-counters {
    description
      "Counters of an indivdual BGP session.";

    leaf flaps {
      type otg-types:counter64;
      description
        "The total number of times the BGP session went from an
        ESTABLISHED state to an IDLE state.";
    }

    leaf in-routes {
      type otg-types:counter64;
      description
        "The total number of routes received.";
    }

    leaf out-routes {
      type otg-types:counter64;
      description
        "The total number of routes advertised.";
    }

    leaf in-route-withdraw {
      type otg-types:counter64;
      description
        "The total number of route withdraws received.";
    }

    leaf out-route-withdraw {
      type otg-types:counter64;
      description
        "The total number of route withdraws sent.";
    }

    leaf in-updates {
      type otg-types:counter64;
      description
        "The total number of UPDATE messages received.";
    }

    leaf out-updates {
      type otg-types:counter64;
      description
        "The total number of UPDATE messages sent.";
    }

    leaf in-opens {
      type otg-types:counter64;
      description
        "The total number of OPEN messages received.";
    }

    leaf out-opens {
      type otg-types:counter64;
      description
        "The total number of OPEN messages sent.";
    }

    leaf in-keepalives {
      type otg-types:counter64;
      description
        "The total number of KEEPALIVE messages received.";
    }

    leaf out-keepalives {
      type otg-types:counter64;
      description
        "The total number of KEEPALIVE messages sent.";
    }

    leaf in-notifications {
      type otg-types:counter64;
      description
        "The total number of NOTIFICATION messages received.";
    }

    leaf out-notifications {
      type otg-types:counter64;
      description
        "The total number of NOTIFICATION messages sent.";
    }

    leaf in-end-of-rib {
      type otg-types:counter64;
      description
        "The total number of End-of-RIB markers received indicating the completion of the initial routing update for a particular <AFI, SAFI> address family after the session is established. For the IPv4 unicast address family, the End-of-RIB marker is an UPDATE message with the minimum length. For any other address family, it is an UPDATE message that contains only the MP_UNREACH_NLRI attribute with no withdrawn routes for that <AFI, SAFI>.";
    }

  }

  grouping bgp-ipv4-prefixes {
    description
      "Structural grouping for unicast ipv4 prefix information";

    container unicast-ipv4-prefixes {
      description
        "Discovered unicast IPv4 prefixes of a BGP peer";

      list unicast-ipv4-prefix {
        key "address prefix-length origin path-id";

        description
          "A list of BGP unicast IPv4 prefixes.";

        leaf address {
          type leafref {
            path "../state/address";
          }
          description
            "Reference to a unicast IPv4 address, acting as part
            of a key to the unicast-ipv4-prefix list.";
        }

        leaf prefix-length {
          type leafref {
            path "../state/prefix-length";
          }
          description
            "Reference to a prefix-length, acting as part of a
            key to the unicast-ipv4-prefix list.";
        }

        leaf origin {
          type leafref {
            path "../state/origin";
          }
          description
            "Reference to an origin, acting as part of a
            key to the unicast-ipv4-prefix list.";
        }

        leaf path-id {
          type leafref {
            path "../state/path-id";
          }
          description
            "Reference to an path-id, acting as part of a
            key to the unicast-ipv4-prefix list.";
        }

        container state {
          description
            "The container for unicast ipv4 prefix state.";

          leaf address {
            type otg-types:ipv4-address;
            description
              "The IPv4 address.";
          }

          leaf prefix-length {
            type uint32;
            description
              "The prefix length.";
          }

          leaf origin {
            type enumeration {
              enum IGP {
                description
                  "The origin is internal.";
              }
              enum EGP {
                description
                  "The origin is external.";
              }
              enum INCOMPLETE {
                description
                  "The origin is neither internal nor external.";
              }
            }
            description
              "The origin of the prefix.";
          }

          leaf path-id {
            type uint32;
            default 0;
            description
              "If the route is learned from a neighbor, the path-id
              corresponds to the path-id for the route in the
              corresponding adj-rib-in-post table.  If the route is
              injected from another protocol, or the neighbor does not
              support BGP add-paths, the path-id should be set
              to zero, also the default value.";
          }

          leaf next-hop-ipv4-address {
            type otg-types:ipv4-address;
            description
              "The IPv4 address of the egress interface.";
          }

          leaf next-hop-ipv6-address {
            type otg-types:ipv6-address;
            description
              "The IPv6 address of the egress interface.";
          }

          list as-path {
            description
              "Unkeyed list of AS PATH segments
              This attribute identifies the autonomous systems through which routing information
              carried in this UPDATE message has passed.";
              uses bgp-as-path-attr-state;
          }

          list community {
            description
              "Unkeyed list of optional community attributes present in the UPDATE message.";
              uses bgp-community-state;
          }

          list extended-community {
            description
              "Unkeyed list of optional extended community attributes present in the UPDATE message.";
              uses bgp-extended-community-state;
          }

          leaf local-preference {
            type uint32;
            description
              "The local preference is a well-known attribute and the value is used for route selection. The route with the highest local preference value is preferred.";
          }

          leaf multi-exit-discriminator {
            type uint32;
            description
              "The multi exit discriminator (MED) is an optional non-transitive attribute and the value is used for route selection. The route with the lowest MED value is preferred.";
          }

        }
      }
    }
  }

  grouping bgp-as-path-attr-state {
    description
      "AS Path segments present in the received AS Path attribute.";
    leaf segment-type {
      type enumeration {
        enum AS_SEQUENCE {
          description
            "Segment type is AS Sequence.";
        }
        enum AS_SET {
          description
            "Segment type is AS Set.";
        }
        enum AS_CONFED_SEQUENCE {
          description
            "Segment type is AS Confederation Sequence";
        }
        enum AS_CONFED_SET {
          description
            "Segment type is AS Confederation Set.";
        }
      }
      description
        "Enumeration of segment types.";
    }
    leaf-list as_numbers {
      type uint32;
      description
        "The AS numbers in this AS path segment.";
    }

  }

  grouping bgp-community-state {
    description
      "the information present in one received Community attribute";
    leaf community-type {
      type enumeration {
        enum MANUAL_AS_NUMBER {
          description
            "Community type is custom.";
        }
        enum NO_EXPORT {
          description
            "Community type is no_export.";
        }
        enum NO_ADVERTISE {
          description
            "Community type is no_advertise.";
        }
        enum NO_EXPORT_SUBCONFED {
          description
            "Community type is no_export_subconfed.";
        }
        enum LLGR_STALE {
          description
            "Community type is llgr_stale.";
        }
        enum NO_LLGR {
          description
            "Community type is no_llgr.";
        }
      }
      description
        "The type of community AS number.";
    }

    uses bgp-community-custom-as-number;
  }

  grouping bgp-community-custom-as-number {
    description
      "Custom as number and as value.";
    leaf custom-as-number {
      type uint16;
      description
        "First two octets of 32 bit community AS number between 0 to 65535.";
    }
    leaf custom-as-value {
      type uint16;
      description
        "Last two octets of 32 bit community AS value between 0 to 65535.";
    }
  }

  grouping transitive_2octet_as {
    description
      "Structural grouping for Transitive Two-Octet AS-Specific Extended Community";

    leaf transitive_2octet_as_type {
      type enumeration {
        enum ROUTE_TARGET_SUBTYPE {
          description
            "Transitive Two-Octet AS-Specific Extended Community is route_target_subtype";
        }
        enum ROUTE_ORIGIN_SUBTYPE {
          description
            "Transitive Two-Octet AS-Specific Extended Community is route_origin_subtype";
        }
        enum LINK_BANDWIDTH_SUBTYPE {
          description
            "Transitive Two-Octet AS-Specific Extended Community is link_bandwidth_subtype";
        }

      }
      description
        "The type of Transitive Two-Octet AS-Specific Extended Community";
    }

    container route_target_subtype {
      config false;
      description
        "The Route Target Community identifies one or more routers that may receive a set of routes (that carry this Community)
        carried by BGP. It is sent with sub-type as 0x02.";

      leaf global_2byte_as {
          type uint16;
          description
            "The two octet IANA assigned AS value assigned to the Autonomous System.";
      }

      leaf local_4byte_admin {
          type uint32;
          description
            "The Local Administrator sub-field contains a number from a numbering space
            that is administered by the organization to which the Autonomous System number
            carried in the Global Administrator sub-field has been assigned by an appropriate authority.";
      }
    }

    container route_origin_subtype {
      config false;
      description
        "The Route Origin Community identifies one or more routers that inject a set of routes (that carry this Community)
        into BGP. It is sent with sub-type as 0x03.";

      leaf global_2byte_as {
          type uint16;
          description
            "The two octet IANA assigned AS value assigned to the Autonomous System.";
      }

      leaf local_4byte_admin {
          type uint32;
          description
            "The Local Administrator sub-field contains a number from a numbering space
            that is administered by the organization to which the Autonomous System number
            carried in the Global Administrator sub-field has been assigned by an appropriate authority.";
      }
    }

    container link_bandwidth_subtype {
      config false;
      description
        "The Link Bandwidth Extended Community attribute is defined in draft-ietf-idr-link-bandwidth. (https://datatracker.ietf.org/doc/draft-ietf-idr-link-bandwidth) It is sent with sub-type as 0x04.";

      leaf global_2byte_as {
          type uint16;
          description
            "The value of the Global Administrator subfield should represent the Autonomous System
            of the router that attaches the Link Bandwidth Community.";
      }

      leaf bandwidth {
          type otg-types:ieeefloat32;
          description
            "Bandwidth of the link in bytes per second. ( 1 Kbps is 1000 bytes per second and 1 Mbps is 1000 Kbps per second )";
      }
    }
  }

  grouping transitive_ipv4_address {
    description
      "Structural grouping for Transitive IPv4 Address Specific Extended Community";

    leaf transitive_ipv4_address_type {
      type enumeration {
        enum ROUTE_TARGET_SUBTYPE {
          description
            "Transitive Two-Octet IPv4 Address Specific Extended Community is route_target_subtype";
        }
        enum ROUTE_ORIGIN_SUBTYPE {
          description
            "Transitive Two-Octet IPv4 Address Specific Extended Community is route_origin_subtype";
        }
      }
      description
        "The type of Transitive IPv4 Address Specific Extended Community";
    }
    container route_target_subtype {
      config false;
      description
        "The Route Target Community identifies one or more routers that may receive a set of routes (that carry this Community)
        carried by BGP. It is sent with sub-type as 0x02.";

      leaf global_ipv4_admin {
          type otg-types:ipv4-address;
          description
            "An IPv4 unicast address assigned by one of the Internet registries.";
      }

      leaf local_2byte_admin {
          type uint16;
          description
            "The Local Administrator sub-field contains a number from a numbering space
            that is administered by the organization to which the IP address carried in the
            Global Administrator sub-field has been assigned by an appropriate authority.";
      }
    }

    container route_origin_subtype {
      config false;
      description
        "The Route Origin Community identifies one or more routers that inject a set of routes (that carry this Community)
        into BGP It is sent with sub-type as 0x03.";

      leaf global_ipv4_admin {
          type otg-types:ipv4-address;
          description
            "An IPv4 unicast address assigned by one of the Internet registries.";
      }

      leaf local_2byte_admin {
          type uint16;
          description
            "The Local Administrator sub-field contains a number from a numbering space
            that is administered by the organization to which the IP address carried in the
            Global Administrator sub-field has been assigned by an appropriate authority.";
      }
    }
  }

  grouping transitive_4octet_as {
    description
      "Structural grouping for Transitive Four-Octet AS-Specific Extended Community";

    leaf transitive_4octet_as_type {
      type enumeration {
        enum ROUTE_TARGET_SUBTYPE {
          description
            "Transitive Four-Octet AS-Specific Extended Community is route_target_subtype";
        }
        enum ROUTE_ORIGIN_SUBTYPE {
          description
            "Transitive Four-Octet AS-Specific Extended Community is route_origin_subtype";
        }
      }
      description
        "The type of Transitive Four-Octet AS-Specific Extended Community";
    }

    container route_target_subtype {
      config false;
      description
        "The Route Target Community identifies one or more routers that may receive a set of routes (that carry this Community)
        carried by BGP. It is sent with sub-type as 0x02.";

      leaf global_4byte_as {
          type uint32;
          description
            "The four octet IANA assigned AS value assigned to the Autonomous System.";
      }

      leaf local_2byte_admin {
          type uint16;
          description
            "The Local Administrator sub-field contains a number from a numbering space that is
            administered by the organization to which the Autonomous System number carried in the
            Global Administrator sub-field has been assigned by an appropriate authority.";
      }
    }

    container route_origin_subtype {
      config false;
      description
        "The Route Origin Community identifies one or more routers that inject a set of routes (that carry this Community)
        into BGP. It is sent with sub-type as 0x03.";

      leaf global_4byte_as {
          type uint32;
          description
            "The four octet IANA assigned AS value assigned to the Autonomous System.";
      }

      leaf local_2byte_admin {
          type uint16;
          description
            "The Local Administrator sub-field contains a number from a numbering space that is
            administered by the organization to which the Autonomous System number carried in the
            Global Administrator sub-field has been assigned by an appropriate authority.";
      }
    }
  }

  grouping transitive_opaque {
    description
      "Structural grouping for Transitive Opaque Extended Community";

    leaf transitive_opaque_type {
      type enumeration {
        enum COLOR_SUBTYPE {
          description
            "Transitive Opaque Extended Community is color_subtype";
        }
        enum ENCAPSULATION_SUBTYPE {
          description
            "Transitive Opaque Extended Community is encapsulation_subtype";
        }
      }
      description
        "The type of Transitive Opaque Extended Community";
    }

    container color_subtype {
      config false;
      description
        "The Color Community contains locally administrator defined 'color' value which is used in conjunction with
        Encapsulation attribute to decide whether a data packet can be transmitted on a certain tunnel or not.
        It is defined in RFC9012 and sent with sub-type as 0x0b.";

      leaf flags {
          type uint16;
          description
            "Two octet flag values.";
      }

      leaf color {
          type uint32;
          description
            "he color value is user defined and configured locally and used to determine whether
            a data packet can be transmitted on a certain tunnel or not in conjunction with the
            Encapsulation attribute. It is defined in RFC9012.";
      }
    }

    container encapsulation_subtype {
      config false;
      description
        "This identifies the type of tunneling technology being signalled.
        It is defined in RFC9012 and sent with sub-type as 0x0c.";

      leaf reserved {
          type uint32;
          description
            "Four bytes of reserved values. Normally set to 0 on transmit and ignored on receive.";
      }

      leaf tunnel_type {
          type uint16;
          description
            "Identifies the type of tunneling technology being signalled.
            Initially defined in RFC5512 and extended in RFC9012.";
      }
    }
  }

  grouping non_transitive_2octet_as {
    description
      "Structural grouping for Non-Transitive Two-Octet AS-Specific Extended Community";

    leaf non_transitive_2octet_as_type {
      type enumeration {
        enum LINK_BANDWIDTH_SUBTYPE {
          description
            "Non-Transitive Two-Octet AS-Specific Extended Community is link_bandwidth_subtype";
        }
      }
      description
        "The type of Non-Transitive Two-Octet AS-Specific Extended Community";
    }

    container link_bandwidth_subtype {
      config false;
      description
        "The Link Bandwidth Extended Community attribute is defined in draft-ietf-idr-link-bandwidth. (https://datatracker.ietf.org/doc/draft-ietf-idr-link-bandwidth) It is sent with sub-type as 0x04.";

      leaf global_2byte_as {
          type uint16;
          description
            "The value of the Global Administrator subfield should represent the Autonomous System
            of the router that attaches the Link Bandwidth Community.";
      }

      leaf bandwidth {
          type otg-types:ieeefloat32;
          description
            "Bandwidth of the link in bytes per second. ( 1 Kbps is 1000 bytes per second and 1 Mbps is 1000 Kbps per second )";
      }
    }
  }

  grouping bgp-extended-community-structured {
    description
      "Structural grouping for Extended Community (structured)";

    leaf bgp-extended-community-structured_type {
      type enumeration {
        enum TRANSITIVE_2OCTET_AS_TYPE {
          description
            "Extended Community type is transitive_2octet_as_type";
        }
        enum TRANSITIVE_IPV4_ADDRESS_TYPE {
          description
            "Extended Community type is transitive_ipv4_address_type";
        }
        enum TRANSITIVE_4OCTET_AS_TYPE {
          description
            "Extended Community type is transitive_4octet_as_type";
        }
        enum TRANSITIVE_OPAQUE_TYPE {
          description
            "Extended Community type is transitive_opaque_type";
        }
        enum NON_TRANSITIVE_2OCTET_AS_TYPE {
          description
            "Extended Community type is non_transitive_2octet_as_type";
        }
      }
      description
        "The type of Extended Community";
    }

    container transitive_2octet_as_type {
      config false;
      description
        "The Transitive Two-Octet AS-Specific Extended Community is sent as type 0x00";
      uses transitive_2octet_as;
    }

    container transitive_ipv4_address_type {
      config false;
      description
        "The Transitive IPv4 Address Specific Extended Community is sent as type 0x01";
      uses transitive_ipv4_address;
    }

    container transitive_4octet_as_type {
      config false;
      description
        "The Transitive Four-Octet AS-Specific Extended Community is sent as type 0x02";
      uses transitive_4octet_as;
    }

    container transitive_opaque_type {
      config false;
      description
        "The Transitive Opaque Extended Community is sent as type 0x03";
      uses transitive_opaque;
    }

    container non_transitive_2octet_as_type {
      config false;
      description
        "The Non-Transitive Two-Octet AS-Specific Extended Community is sent as type 0x40";
      uses non_transitive_2octet_as;
    }
  }

  grouping bgp-extended-community-state {
    description
      "the information present in one received Extended Community attribute";
    leaf raw {
      type otg-types:hex-string;
      description
        "The raw byte contents of the 8 bytes received in the Extended Community as 16 hex characters.";
    }

    container structured {
      config false;
      description
        "The structured representation of the 8 bytes received in the Extended Community";
      uses bgp-extended-community-structured;
    }
  }

  grouping bgp-ipv6-prefixes {
    description
      "Structural grouping for unicast ipv6 prefix information";

    container unicast-ipv6-prefixes {
      description
        "Discovered unicast IPv6 prefixes of a BGP peer";

      list unicast-ipv6-prefix {
        key "address prefix-length origin path-id";

        description
          "A list of BGP unicast IPv6 prefixes.";

        leaf address {
          type leafref {
            path "../state/address";
          }
          description
            "Reference to a unicast IPv6 address, acting as part
            of a key to the unicast-ipv6-prefix list.";
        }

        leaf prefix-length {
          type leafref {
            path "../state/prefix-length";
          }
          description
            "Reference to a prefix-length, acting as part of a
            key to the unicast-ipv6-prefix list.";
        }

        leaf origin {
          type leafref {
            path "../state/origin";
          }
          description
            "Reference to an origin, acting as part of a
            key to the unicast-ipv6-prefix list.";
        }

        leaf path-id {
          type leafref {
            path "../state/path-id";
          }
          description
            "Reference to an path-id, acting as part of a
            key to the unicast-ipv6-prefix list.";
        }

        container state {
          description
            "The container for unicast IPv6 prefix state.";

          leaf address {
            type otg-types:ipv6-address;
            description
              "The IPv6 address.";
          }

          leaf prefix-length {
            type uint32;
            description
              "The prefix length.";
          }

          leaf origin {
            type enumeration {
              enum IGP {
                description
                  "The origin is internal.";
              }
              enum EGP {
                description
                  "The origin is external.";
              }
              enum INCOMPLETE {
                description
                  "The origin is neither internal nor external.";
              }
            }
            description
              "The origin of the prefix.";
          }

          leaf path-id {
            type uint32;
            default 0;
            description
              "If the route is learned from a neighbor, the path-id
              corresponds to the path-id for the route in the
              corresponding adj-rib-in-post table.  If the route is
              injected from another protocol, or the neighbor does not
              support BGP add-paths, the path-id should be set
              to zero, also the default value.";
          }

          leaf next-hop-ipv4-address {
            type otg-types:ipv4-address;
            description
              "The IPv4 address of the egress interface.";
          }

          leaf next-hop-ipv6-address {
            type otg-types:ipv6-address;
            description
              "The IPv6 address of the egress interface.";
          }

          list as-path {
            description
              "Unkeyed list of AS PATH segments
              This attribute identifies the autonomous systems through which routing information
              carried in this UPDATE message has passed.";
              uses bgp-as-path-attr-state;
          }

          list community {
            description
              "Unkeyed list of optional community attributes present in the UPDATE message.";
              uses bgp-community-state;
          }

          list extended-community {
            description
              "Unkeyed list of optional extended community attributes present in the UPDATE message.";
              uses bgp-extended-community-state;
          }

          leaf local-preference {
            type uint32;
            description
              "The local preference is a well-known attribute and the value is used for route selection. The route with the highest local preference value is preferred.";
          }

          leaf multi-exit-discriminator {
            type uint32;
            description
              "The multi exit discriminator (MED) is an optional non-transitive attribute and the value is used for route selection. The route with the lowest MED value is preferred.";
          }

        }
      }
    }
  }

  grouping mpls-ipv4-prefixes {
    description
      "Structural grouping for ipv4 MPLS unicast prefix information";

    container ipv4-mpls-unicast-prefixes {
      description
        "Discovered MPLS unicast IPv4 prefixes of a BGP peer";

      list ipv4-mpls-unicast-prefix {
        key "address prefix-length origin path-id";

        description
          "A list of BGP unicast IPv4 prefixes.";

        leaf address {
          type leafref {
            path "../state/address";
          }
          description
            "Reference to IPv4 address, acting as part
            of a key to the MPLS unicast-ipv4-prefix list.";
        }

        leaf prefix-length {
          type leafref {
            path "../state/prefix-length";
          }
          description
            "Reference to a prefix-length, acting as part of a
            key to the MPLS unicast-ipv4-prefix list.";
        }

        leaf origin {
          type leafref {
            path "../state/origin";
          }
          description
            "Reference to an origin, acting as part of a
            key to the MPLS unicast-ipv4-prefix list.";
        }

        leaf path-id {
          type leafref {
            path "../state/path-id";
          }
          description
            "Reference to an path-id, acting as part of a
            key to the MPLS unicast-ipv4-prefix list.";
        }

        container state {
          description
            "The container for MPLS unicast ipv4 prefix state.";

          leaf address {
            type otg-types:ipv4-address;
            description
              "The IPv4 address.";
          }

          leaf prefix-length {
            type uint32;
            description
              "The prefix length.";
          }

          leaf origin {
            type enumeration {
              enum IGP {
                description
                  "The origin is internal.";
              }
              enum EGP {
                description
                  "The origin is external.";
              }
              enum INCOMPLETE {
                description
                  "The origin is neither internal nor external.";
              }
            }
            description
              "The origin of the prefix.";
          }

          leaf path-id {
            type uint32;
            default 0;
            description
              "If the route is learned from a neighbor, the path-id
              corresponds to the path-id for the route in the
              corresponding adj-rib-in-post table.  If the route is
              injected from another protocol, or the neighbor does not
              support BGP add-paths, the path-id should be set
              to zero, also the default value.";
          }

          leaf next-hop-ipv4-address {
            type otg-types:ipv4-address;
            description
              "The IPv4 address of the egress interface.";
          }

          leaf next-hop-ipv6-address {
            type otg-types:ipv6-address;
            description
              "The IPv6 address of the egress interface.";
          }

         list labels {
            description
              "Unkeyed list of MPLS labels associated with the prefix.";
            leaf label {
              type otg-types:mpls-label;
              description
                "The MPLS label value.";
            }
          }

          list as-path {
            description
              "Unkeyed list of AS PATH segments
              This attribute identifies the autonomous systems through which routing information
              carried in this UPDATE message has passed.";
              uses bgp-as-path-attr-state;
          }

          list community {
            description
              "Unkeyed list of optional community attributes present in the UPDATE message.";
              uses bgp-community-state;
          }

          list extended-community {
            description
              "Unkeyed list of optional extended community attributes present in the UPDATE message.";
              uses bgp-extended-community-state;
          }

          leaf local-preference {
            type uint32;
            description
              "The local preference is a well-known attribute and the value is used for route selection. The route with the highest local preference value is preferred.";
          }

          leaf multi-exit-discriminator {
            type uint32;
            description
              "The multi exit discriminator (MED) is an optional non-transitive attribute and the value is used for route selection. The route with the lowest MED value is preferred.";
          }

        }
      }
    }
  }

  grouping mpls-ipv6-prefixes {
    description
      "Structural grouping for MPLS unicast ipv6 prefix information";

    container ipv6-mpls-unicast-prefixes {
      description
        "Discovered MPLS unicast IPv6 prefixes of a BGP peer";

      list ipv6-mpls-unicast-prefix {
        key "address prefix-length origin path-id";

        description
          "A list of BGP unicast IPv6 prefixes.";

        leaf address {
          type leafref {
            path "../state/address";
          }
          description
            "Reference to a IPv6 address, acting as part
            of a key to the MPLS unicast-ipv6-prefix list.";
        }

        leaf prefix-length {
          type leafref {
            path "../state/prefix-length";
          }
          description
            "Reference to a prefix-length, acting as part of a
            key to the MPLS unicast-ipv6-prefix list.";
        }

        leaf origin {
          type leafref {
            path "../state/origin";
          }
          description
            "Reference to an origin, acting as part of a
            key to the MPLS unicast-ipv6-prefix list.";
        }

        leaf path-id {
          type leafref {
            path "../state/path-id";
          }
          description
            "Reference to an path-id, acting as part of a
            key to the MPLS unicast-ipv6-prefix list.";
        }

        container state {
          description
            "The container for MPLS unicast IPv6 prefix state.";

          leaf address {
            type otg-types:ipv6-address;
            description
              "The IPv6 address.";
          }

          leaf prefix-length {
            type uint32;
            description
              "The prefix length.";
          }

          leaf origin {
            type enumeration {
              enum IGP {
                description
                  "The origin is internal.";
              }
              enum EGP {
                description
                  "The origin is external.";
              }
              enum INCOMPLETE {
                description
                  "The origin is neither internal nor external.";
              }
            }
            description
              "The origin of the prefix.";
          }

          leaf path-id {
            type uint32;
            default 0;
            description
              "If the route is learned from a neighbor, the path-id
              corresponds to the path-id for the route in the
              corresponding adj-rib-in-post table.  If the route is
              injected from another protocol, or the neighbor does not
              support BGP add-paths, the path-id should be set
              to zero, also the default value.";
          }

          leaf next-hop-ipv4-address {
            type otg-types:ipv4-address;
            description
              "The IPv4 address of the egress interface.";
          }

          leaf next-hop-ipv6-address {
            type otg-types:ipv6-address;
            description
              "The IPv6 address of the egress interface.";
          }
          list labels {
            description
              "Unkeyed list of MPLS labels associated with the prefix.";
            leaf label {
              type otg-types:mpls-label;
              description
                "The MPLS label value.";
            }
          }

          list as-path {
            description
              "Unkeyed list of AS PATH segments
              This attribute identifies the autonomous systems through which routing information
              carried in this UPDATE message has passed.";
              uses bgp-as-path-attr-state;
          }

          list community {
            description
              "Unkeyed list of optional community attributes present in the UPDATE message.";
              uses bgp-community-state;
          }

          list extended-community {
            description
              "Unkeyed list of optional extended community attributes present in the UPDATE message.";
              uses bgp-extended-community-state;
          }

          leaf local-preference {
            type uint32;
            description
              "The local preference is a well-known attribute and the value is used for route selection. The route with the highest local preference value is preferred.";
          }

          leaf multi-exit-discriminator {
            type uint32;
            description
              "The multi exit discriminator (MED) is an optional non-transitive attribute and the value is used for route selection. The route with the lowest MED value is preferred.";
          }

        }
      }
    }
  }

  grouping mpls-vpn-ipv4-prefixes {
    description
      "Structural grouping for VPN-IPv4 (L3VPN, RFC 4364) MPLS unicast prefix
      information.";

    container ipv4-mpls-vpn-unicast-prefixes {
      description
        "VPN-IPv4 (AFI 1, SAFI 128) MPLS unicast prefixes discovered from the
        peer, reported grouped by the local VRF(s) they were imported into
        via Route Target matching (RFC 4364 Section 4.3.1).";

      leaf ipv4-mpls-vpn-unicast-prefixes_type {
        type enumeration {
          enum MATCHED_VRF_ROUTES {
            description
              "Prefixes are grouped by the local VRF(s) they were matched
              into.";
          }
        }
        description
          "Selects how VPN-IPv4 prefixes are reported. Currently the only
          supported view groups them by matched local VRF.";
      }

      container matched_vrf_routes {
        config false;

        description
          "The local VRFs that received VPN-IPv4 NLRIs were imported into,
          each with its own list of matched routes.";

        list vrf {
          key "name";

          config false;

          description
            "A single local VRF and the VPN-IPv4 routes imported into it.
            The same VPN-IPv4 NLRI can be imported into more than one VRF,
            in which case it appears under each matching VRF's routes.";

          leaf name {
            type leafref {
              path "../state/name";
            }
            description
              "Reference to the VRF name, acting as the key to the vrf
              list.";
          }

          container state {
            config false;

            description
              "The container for VRF-grouped VPN-IPv4 route state.";

            leaf name {
              type string;
              description
                "The name of the local VRF that imported these routes.";
            }
          }

          list route {
            key "route-distinguisher address prefix-length origin path-id";

            config false;

            description
              "A VPN-IPv4 prefix imported into this VRF, with the path
              attributes received for that NLRI.";

            leaf route-distinguisher {
              type leafref {
                path "../state/route-distinguisher";
              }
              description
                "Reference to a route distinguisher, acting as part of a
                key to the route list.";
            }

            leaf address {
              type leafref {
                path "../state/address";
              }
              description
                "Reference to the IPv4 address, acting as part of a key to
                the route list.";
            }

            leaf prefix-length {
              type leafref {
                path "../state/prefix-length";
              }
              description
                "Reference to a prefix-length, acting as part of a key to
                the route list.";
            }

            leaf origin {
              type leafref {
                path "../state/origin";
              }
              description
                "Reference to an origin, acting as part of a key to the
                route list.";
            }

            leaf path-id {
              type leafref {
                path "../state/path-id";
              }
              description
                "Reference to a path-id, acting as part of a key to the
                route list.";
            }

            container state {
              config false;

              description
                "The container for VPN-IPv4 route state.";

              leaf route-distinguisher {
                type string;
                description
                  "The route distinguisher (RFC 4364 Section 4.2) that the
                  prefix was received with.";
              }

              leaf address {
                type otg-types:ipv4-address;
                description
                  "The IPv4 address.";
              }

              leaf prefix-length {
                type uint32;
                description
                  "The prefix length.";
              }

              leaf origin {
                type enumeration {
                  enum IGP {
                    description
                      "The origin is internal.";
                  }
                  enum EGP {
                    description
                      "The origin is external.";
                  }
                  enum INCOMPLETE {
                    description
                      "The origin is neither internal nor external.";
                  }
                }
                description
                  "The origin of the prefix.";
              }

              leaf path-id {
                type uint32;
                default 0;
                description
                  "If the route is learned from a neighbor, the path-id
                  corresponds to the path-id for the route in the
                  corresponding adj-rib-in-post table.  If the route is
                  injected from another protocol, or the neighbor does not
                  support BGP add-paths, the path-id should be set
                  to zero, also the default value.";
              }

              leaf next-hop-ipv4-address {
                type otg-types:ipv4-address;
                description
                  "The IPv4 address of the egress interface.";
              }

              leaf next-hop-ipv6-address {
                type otg-types:ipv6-address;
                description
                  "The IPv6 address of the egress interface.";
              }

              leaf label {
                type otg-types:mpls-label;
                description
                  "The single VPN dataplane MPLS label (RFC 4364 Section 3)
                  bound to this prefix.";
              }

              list as-path {
                description
                  "Unkeyed list of AS PATH segments
                  This attribute identifies the autonomous systems through which routing information
                  carried in this UPDATE message has passed.";
                  uses bgp-as-path-attr-state;
              }

              list community {
                description
                  "Unkeyed list of optional community attributes present in the UPDATE message.";
                  uses bgp-community-state;
              }

              list extended-community {
                description
                  "Unkeyed list of optional extended community attributes present in the UPDATE message.";
                  uses bgp-extended-community-state;
              }

              leaf local-preference {
                type uint32;
                description
                  "The local preference is a well-known attribute and the value is used for route selection. The route with the highest local preference value is preferred.";
              }

              leaf multi-exit-discriminator {
                type uint32;
                description
                  "The multi exit discriminator (MED) is an optional non-transitive attribute and the value is used for route selection. The route with the lowest MED value is preferred.";
              }

            }
          }
        }
      }
    }
  }

  grouping mpls-vpn-ipv6-prefixes {
    description
      "Structural grouping for VPN-IPv6 (6VPE, RFC 4659) MPLS unicast prefix
      information.";

    container ipv6-mpls-vpn-unicast-prefixes {
      description
        "VPN-IPv6 (AFI 2, SAFI 128) MPLS unicast prefixes discovered from the
        peer, reported grouped by the local VRF(s) they were imported into
        via Route Target matching (RFC 4364 Section 4.3.1).";

      leaf ipv6-mpls-vpn-unicast-prefixes_type {
        type enumeration {
          enum MATCHED_VRF_ROUTES {
            description
              "Prefixes are grouped by the local VRF(s) they were matched
              into.";
          }
        }
        description
          "Selects how VPN-IPv6 prefixes are reported. Currently the only
          supported view groups them by matched local VRF.";
      }

      container matched_vrf_routes {
        config false;

        description
          "The local VRFs that received VPN-IPv6 NLRIs were imported into,
          each with its own list of matched routes.";

        list vrf {
          key "name";

          config false;

          description
            "A single local VRF and the VPN-IPv6 routes imported into it.
            The same VPN-IPv6 NLRI can be imported into more than one VRF,
            in which case it appears under each matching VRF's routes.";

          leaf name {
            type leafref {
              path "../state/name";
            }
            description
              "Reference to the VRF name, acting as the key to the vrf
              list.";
          }

          container state {
            config false;

            description
              "The container for VRF-grouped VPN-IPv6 route state.";

            leaf name {
              type string;
              description
                "The name of the local VRF that imported these routes.";
            }
          }

          list route {
            key "route-distinguisher address prefix-length origin path-id";

            config false;

            description
              "A VPN-IPv6 prefix imported into this VRF, with the path
              attributes received for that NLRI.";

            leaf route-distinguisher {
              type leafref {
                path "../state/route-distinguisher";
              }
              description
                "Reference to a route distinguisher, acting as part of a
                key to the route list.";
            }

            leaf address {
              type leafref {
                path "../state/address";
              }
              description
                "Reference to the IPv6 address, acting as part of a key to
                the route list.";
            }

            leaf prefix-length {
              type leafref {
                path "../state/prefix-length";
              }
              description
                "Reference to a prefix-length, acting as part of a key to
                the route list.";
            }

            leaf origin {
              type leafref {
                path "../state/origin";
              }
              description
                "Reference to an origin, acting as part of a key to the
                route list.";
            }

            leaf path-id {
              type leafref {
                path "../state/path-id";
              }
              description
                "Reference to a path-id, acting as part of a key to the
                route list.";
            }

            container state {
              config false;

              description
                "The container for VPN-IPv6 route state.";

              leaf route-distinguisher {
                type string;
                description
                  "The route distinguisher (RFC 4364 Section 4.2) that the
                  prefix was received with.";
              }

              leaf address {
                type otg-types:ipv6-address;
                description
                  "The IPv6 address.";
              }

              leaf prefix-length {
                type uint32;
                description
                  "The prefix length.";
              }

              leaf origin {
                type enumeration {
                  enum IGP {
                    description
                      "The origin is internal.";
                  }
                  enum EGP {
                    description
                      "The origin is external.";
                  }
                  enum INCOMPLETE {
                    description
                      "The origin is neither internal nor external.";
                  }
                }
                description
                  "The origin of the prefix.";
              }

              leaf path-id {
                type uint32;
                default 0;
                description
                  "If the route is learned from a neighbor, the path-id
                  corresponds to the path-id for the route in the
                  corresponding adj-rib-in-post table.  If the route is
                  injected from another protocol, or the neighbor does not
                  support BGP add-paths, the path-id should be set
                  to zero, also the default value.";
              }

              leaf next-hop-ipv4-address {
                type otg-types:ipv4-address;
                description
                  "The IPv4 address of the egress interface.";
              }

              leaf next-hop-ipv6-address {
                type otg-types:ipv6-address;
                description
                  "The IPv6 address of the egress interface.";
              }

              container service-binding {
                config false;

                description
                  "The VPN dataplane binding received for this VPN-IPv6
                  prefix, mirroring the Bgp.L3vpn.V6ServiceBinding choice
                  on the configured route range.";

                leaf service-binding_type {
                  type enumeration {
                    enum LABEL {
                      description
                        "The dataplane binding is a VPN MPLS label.";
                    }
                  }
                  description
                    "The VPN dataplane encoding received for this route.";
                }

                leaf label {
                  type otg-types:mpls-label;
                  description
                    "The single VPN dataplane MPLS label (RFC 4364
                    Section 3, RFC 4659) bound to this prefix.";
                }
              }

              list as-path {
                description
                  "Unkeyed list of AS PATH segments
                  This attribute identifies the autonomous systems through which routing information
                  carried in this UPDATE message has passed.";
                  uses bgp-as-path-attr-state;
              }

              list community {
                description
                  "Unkeyed list of optional community attributes present in the UPDATE message.";
                  uses bgp-community-state;
              }

              list extended-community {
                description
                  "Unkeyed list of optional extended community attributes present in the UPDATE message.";
                  uses bgp-extended-community-state;
              }

              leaf local-preference {
                type uint32;
                description
                  "The local preference is a well-known attribute and the value is used for route selection. The route with the highest local preference value is preferred.";
              }

              leaf multi-exit-discriminator {
                type uint32;
                description
                  "The multi exit discriminator (MED) is an optional non-transitive attribute and the value is used for route selection. The route with the lowest MED value is preferred.";
              }

            }
          }
        }
      }
    }
  }

  uses bgp-top;
}
