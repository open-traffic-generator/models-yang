module open-traffic-generator-dhcpv4client {
  yang-version "1";

  namespace "http://gitub.com/open-traffic-generator/models-yang/models/dhcp/v4client";
  prefix "otg-dhcpv4client";

  import open-traffic-generator-types {
    prefix "otg-types";
  }

  organization
    "OpenTrafficGenerator working group";

  contact
    "OpenTrafficGenerator working group
     opentrafficgenerator@googlegroups.com";

  description
    "This module defines telemetry that relates OTG to dhcpv4client sessions that
    are controlled by an open traffic generator (OTG) whose definition
    is outside of the context of this module.";

  revision 2024-04-10 {
    description "Initial revision.";
    reference "0.1.0";
  }

  grouping dhcpv4clients-top {
    description
      "Top-level structural grouping for DHCPv4 Client telemetry
      entries.";
    reference
      "1. https://redocly.github.io/redoc/?url=https://raw.githubusercontent.com/open-traffic-generator/models/dhcp_support_support/artifacts/openapi.yaml&nocors";

    container dhcpv4-clients {
      description
        "DHCPv4 Clients telemetry collected by the OTG device.";

      list dhcpv4-client {
        key "name";

        config false;

        description
          "Each DHCPv4 Client is identified by an arbitrary string
          identifier.";

        leaf name {
          type leafref {
            path "../state/name";
          }
          description
            "Reference to the DHCPv4 Client's name, acting as a key of
            the DHCPv4 Client list.";
        }

        container state {
          config false;
          description
            "Operational state of an individual DHCPv4 Client.";
          uses dhcpv4client-state;
        }
      }
    }
  }

  grouping dhcpv4client-state {
    description
      "Operational state of an individual DHCPv4 Client.";

    leaf name {
      type string;
      description
        "An arbitrary name of the DHCPv4 Client determined by the OTG
        configuration.";
    }

    container counters {
      description
        "Counters of an indivdual DHCPv4 session.";

      uses dhcp4client-counters;
    }
    container interface {
      description
        "Information about address learned by an indivdual DHCPv4 session.";

      uses dhcp4-interface;
    }
  }

  grouping dhcp4client-counters {
    description
      "Counters of the DHCPv4 Client.";
    leaf discovers-sent {
      type otg-types:counter64;
      description
        "Number of DHCPDISCOVER messages sent.";
    }
    leaf offers-received {
      type otg-types:counter64;
      description
        "Number of DHCPOFFER messages received.";
    }
    leaf requests-sent {
      type otg-types:counter64;
      description
        "Number of DHCPREQUEST messages sent.";
    }
    leaf acks-received {
      type otg-types:counter64;
      description
        "Number of DHCPACKS messages received.";
    }
    leaf nacks-received {
      type otg-types:counter64;
      description
        "Number of DHCPNACKS messages received.";
    }
    leaf releases-sent {
      type otg-types:counter64;
      description
        "Number of DHCPRELEASE messages sent.";
    }
    leaf declines-sent {
      type otg-types:counter64;
      description
        "Number of DHCPDECLINE messages sent.";
    }
  }

  grouping dhcp4-interface {
    description
      "This grouping defines learning of IPv4 address information.";
    leaf address {
      type otg-types:ipv4-address;
      description
        "The IPv4 address associated with this DHCP Client session.";
    }

    leaf prefix-length {
      type uint32;
      description
        "The length of the prefix";
    }

    leaf gateway_address {
      type otg-types:ipv4-address;
      description
        "The Gateway address associated with the DHCP Client session.";
    }
    leaf lease_time {
      type uint32;
      description
        "The duration of the IP address lease, in seconds.";
    }
    leaf renew_time {
      type uint32;
      description
        "Time in seconds until the DHCPv4 client starts renewing the lease.";
    }
    leaf rebind_time {
      type uint32;
      description
        "Time in seconds until the DHCPv4 client starts rebinding.";
    }
  }

  uses dhcpv4clients-top;
}
