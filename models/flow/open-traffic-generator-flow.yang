module open-traffic-generator-flow {
  yang-version "1";

  namespace "http://github.com/open-traffic-generator/models/yang/models/flow";
  prefix "otg-flow";

  import open-traffic-generator-types {
    prefix "otg-types";
  }

  organization
    "OpenTrafficGenerator working group";

  contact
    "OpenTrafficGenerator working group
     opentrafficgenerator@googlegroups.com";

  description
    "This module defines telemetry that refers to dataplane flows that
    are controlled by an open traffic generator (OTG) whose definition
    is outside of the context of this module.";

  revision 2022-01-21 {
    description "Initial revision.";
    reference "0.1.0";
  }

  grouping flow-top {
    description
      "Top-level structural grouping for flow entries.";

    container flows {
      description
        "Flow statistics collected by the network device.
        A flow is defined to be an arbitrary stream of packets whose
        definition is outside of the context of the module.";

      list flow {
        key "name";

        config false;

        description
          "A flow of packets between one or more internal and external sources
          and one or more internal and external destinations that the target
          is able to track and report statistics on. Each flow is identified by
          an arbitrary string identifier.";

        leaf name {
          type leafref {
            path "../state/name";
          }
          description
            "Reference to the flow's name, acting as a key of the
            flow list.";
        }

        container state {
          config false;

          description
            "Operational state of the individual flow.";

          uses flow-state;

          container counters {
            description
              "Counters that correspond to the individual flow.";

            uses flow-counters;
          }
        }

        uses tagged-metrics;
      }
    }
  }

  grouping flow-state {
    description
      "Operational state of the individual flow.";

    leaf name {
      type string;
      description
        "An arbitrary name used for the flow tracked by the system. This
        name must be unique for the flows tracked and exported by the target.";
    }

    leaf transmit {
      type boolean;
      description
        "Whether or not the flow is transmitting";
    }

    leaf loss-pct {
      type otg-types:ieeefloat32;
      description
        "The percentage of transmitted packets that were not received by the
        destinations of the flow.";
    }

    leaf out-frame-rate {
      type otg-types:ieeefloat32;
      description
        "The rate, measured in frames per second, at which frames are being
        transmitted for the flow.";
    }

    leaf in-frame-rate {
      type otg-types:ieeefloat32;
      description
        "The rate, measured in frames per second, at which frames are being
        received for the flow.";
    }

    leaf out-rate {
      type otg-types:ieeefloat32;
      description
        "The rate, measured in bits per second, at which the flow is being
        transmitted.";
    }

    leaf in-rate {
      type otg-types:ieeefloat32;
      description
        "The rate, measured in bits per second, at which the flow is being
        received.";
    }

    leaf out-l1-rate {
      type otg-types:ieeefloat32;
      description
        "The rate, measured in bits per second, at which the flow is being
        transmitted from the Layer 1.";
    }

    leaf in-l1-rate {
      type otg-types:ieeefloat32;
      description
        "The rate, measured in bits per second, at which the flow is being
        received in the Layer 1.";
    }

    leaf minimum-latency {
      type otg-types:timeticks64;
      description
        "The minimum latency value, measured in nanoseconds. The latency value is dependent
        on the configured type of latency measurement mode.";
    }

    leaf maximum-latency {
      type otg-types:timeticks64;
      description
        "The maximum latency value, measured in nanoseconds. The latency value is dependent
        on the configured type of latency measurement mode.";
    }

    leaf average-latency {
      type otg-types:timeticks64;
      description
        "The average latency value, measured in nanoseconds. The latency value is dependent
        on the configured type of latency measurement mode.";
    }

    leaf first-timestamp {
      type decimal64 {
        fraction-digits 2;
      }
      description
        "The received timestamp for the first incoming packet, measured in nanoseconds. Timestamp will be reset every time a flow is started.";
    }

    leaf last-timestamp {
      type decimal64 {
        fraction-digits 2;
      }
      description
        "The received timestamp for the last incoming packet, measured in nanoseconds. Timestamp will be reset every time a flow is started.";
    }
  }

  grouping flow-counters {
    description
      "Counters that correspond to an individual flow.";

    leaf in-octets {
      type otg-types:counter64;
      description
        "The total number of bytes received by the target for the flow.";
    }

    leaf in-pkts {
      type otg-types:counter64;
      description
        "The total number of packets received by the target for the flow.";
    }

    leaf out-octets {
      type otg-types:counter64;
      description
        "The total number of bytes sent by the target for the flow. These
        packets may be generated or forwarded by the target.";
    }

    leaf out-pkts {
      type otg-types:counter64;
      description
        "The total number of packets sent by the target for the flow. These
        packets may be generated or forwarded by the target.";
    }
  }

  grouping tagged-metrics {
    description
      "Structural grouping for tagged-metrics information";

    container tagged-metrics {
      description
        "Container of tagged metric information.";

      list tagged-metric {
        key "name-value-pairs";

        description
          "A list of enumerated metric, based on all metric tags present in the configuration.
          Each enumerated metric is identified by a name-value-pairs";

        leaf name-value-pairs {
          type leafref {
            path "../state/name-value-pairs";
          }
          description
            "Reference to a name-value-pairs, acting as
            a key of the tagged-metric list.";
        }

        container state {
          description
            "Operational state of the individual tagged-metric.";

          leaf name-value-pairs {
            type string;
            description
              "Encoded string represents one or more metric tag names and corresponding tag value,
              to identify each enumerated flow.
              Encoding format:
                  tag_name=value&tag_name=value
              In encoded string, metric tags MUST be arranged in alphabetical order of the tag name. And tag value(s) in lowercase only.
              Example:
                ipv4_src=0x11
                ipv4_src=0x11&vlan_id=0x12ab
                ipv4_dst=2.2.2.2&mpls_label=1000
              Incorrect encoding example:
                vlan_id=0x12AB                  // value in uppercase
                vlan_id=0x12ab&ipv4_src=0x11    // tag name not in alphabetical order
              Note:
                  If the metric tag is set to match a packet field partially, the value format will be in hex
                  (e.g. tag set on last 8 bits of the IPv4 Src field)
                  However, if the metric tag is enabled for the entire packet field, the value will be in the native format of the field
                  (e.g. value format in IPv4 address if the metric tag is set for the entire IPv4 Dst field)";
          }

          list tags {
            description
              "A list of metric tag names and associated tag values, in a structured manner to identify each enumerated flow.";

            leaf tag-name {
              type string;
              description
                "The name of the metric tag corresponding to this enumerated flow.";
            }

            container tag-value {
              description
                "The value of the metric tag corresponding to this enumerated flow.
                Value format is based on the metric tag configuration of the Flow";

              leaf value-type {
                type enumeration {
                  enum STRING {
                    description
                      "Indicates Tag value in String format. Only 'value-as-string' contains the value";
                  }
                  enum HEX {
                    description
                      "Indicates Tag value in Hex String format. Only 'value-as-hex' contains the value";
                  }
                  enum BOOL {
                    description
                      "Indicates Tag value in Boolean format. Only 'value-as-bool' contains the value";
                  }
                  enum COUNTER64 {
                    description
                      "Indicates Tag value in counter64 (64-bit unsigned number) format. Only 'value-as-counter64' contains the value";
                  }
                  enum FLOAT32 {
                    description
                      "Indicates Tag value in 32-bit floating point number format. Only 'value-as-float32' contains the value";
                  }
                  enum IPV4 {
                    description
                      "Indicates Tag value in IPv4 address format. Only 'value-as-ipv4' contains the value";
                  }
                  enum IPV6 {
                    description
                      "Indicates Tag value in IPv6 address format. Only 'value-as-ipv6' contains the value";
                  }
                  enum MAC {
                    description
                      "Indicates Tag value in MAC address format. Only 'value-as-mac' contains the value";
                  }
                }
                description
                  "Indicates the format of the tag value. Based on the format, only one 'value-as-*' field will be populated.";
              }

              leaf value-as-string {
                type string;
                description
                  "Contains Tag Value in String format.";
              }

              leaf value-as-hex {
                type otg-types:hex-string-prefixed;
                description
                  "Contains Tag Value in Hexadecimal format which is prefixed with 0x or 0X.";
              }

              leaf value-as-bool {
                type boolean;
                description
                  "Contains Tag Value in Boolean format.";
              }

              leaf value-as-counter64 {
                type otg-types:counter64;
                description
                  "Contains Tag Value in Counter64 (64-bit unsigned number) format.";
              }

              leaf value-as-float32 {
                type otg-types:ieeefloat32;
                description
                  "Contains Tag Value in 32-bit floating point number format.";
              }

              leaf value-as-ipv4 {
                type otg-types:ipv4-address;
                description
                  "Contains Tag Value in IPv4 address format.";
              }

              leaf value-as-ipv6 {
                type otg-types:ipv6-address;
                description
                  "Contains Tag Value in IPv6 address format.";
              }

              leaf value-as-mac {
                type otg-types:mac-address;
                description
                  "Contains Tag Value in MAC address format.";
              }
            }
          }

          container counters {
            description
              "Counters that correspond to the enumerated flow metrics associated
              with a name-value-pairs as identifier of that enumerated flow.";

            uses flow-counters;
          }
        }
      }
    }
  }

  uses flow-top;
}
