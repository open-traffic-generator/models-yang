module open-traffic-generator-isis {
  yang-version "1";

  namespace "http://gitub.com/open-traffic-generator/models-yang/models/isis";
  prefix "otg-isis";

  import open-traffic-generator-types {
    prefix "otg-types";
  }

  organization
    "OpenTrafficGenerator working group";

  contact
    "OpenTrafficGenerator working group
     opentrafficgenerator@googlegroups.com";

  description
    "This module defines telemetry that relOTGs to ISIS sessions that
    are controlled by an open traffic generator (OTG) whose definition
    is outside of the context of this module.";

  revision 2022-01-21 {
    description "Initial revision.";
    reference "0.1.0";
  }

  grouping isis-top {
    description
      "Top-level structural grouping for ISIS router telemetry
      entries.";

    container isis-routers {
      description
        "ISIS router telemetry collected by the OTG device.";

      list isis-router {
        key "name";

        config false;

        description
          "Each ISIS router is identified by an arbitrary string
          identifier.";

        leaf name {
          type leafref {
            path "../state/name";
          }
          description
            "Reference to the ISIS router's name, acting as a key of
            the ISIS router list.";
        }

        container state {
          description
            "Operational state of an individual ISIS router.";
          uses isis-state;
        }
      }
    }
  }

  grouping isis-state {
    description
      "Operational state of an individual ISIS router.";

    leaf name {
      type string;
      description
        "An arbitrary name of the ISIS router determined by the OTG
        configuration.";
    }

    container counters {
      description
        "Level counters of the ISIS router.";

      uses isis-level-counters;
    }

    container link-state-database {
      description
        "This sub-module describes a YANG model for the IS-IS Link State
         Database (LSDB)";

      uses lsp-states;
    }
    container adjacencies {
      description
        "This sub-module describes a YANG model for the IS-IS IIH information exchanged between the IS-IS routers.";
      uses adjacency-states;
    }
  }

  grouping isis-level-counters {
    description
      "Operational level counters of the ISIS router.";

    container level1 {
      description
        "Level1 counters of the ISIS router.";
      uses isis-counters;
    }

    container level2 {
      description
        "Level2 counters of the ISIS router.";
      uses isis-counters;
    }
    leaf gr-initiated {
      type otg-types:counter64;
      description
        "Number of Graceful Restarts that were initiated by this router.";
    }

    leaf gr-succeeded {
      type otg-types:counter64;
      description
        "Number of Graceful Restarts succeeded that were initiated by a this router.
        This counter is incremented if the Graceful Restart completes successfully before the T3 timer expires.
        Timer T3 is maintained for the entire system after which the router will declare that it has failed to achieve database synchronization.";
    }

    leaf neighbor-gr-initiated {
      type otg-types:counter64;
      description
        "Number of Graceful Restarts that were initiated by a Neighbor. This counter is incremented for Restart TLV having RR bit is set present in the received IIH PDU.";
    }

    leaf neighbor-gr-succeeded {
      type otg-types:counter64;
      description
        "Number of Graceful Restarts succeeded that were initiated by a Neighbor.
        This counter is incremented when Restart TLV having RR bit is unset present in the received IIH PDU after the Graceful Restart was initiated by a Neighbor.";
    }
  }

  grouping lsp-states {
    description
      "This grouping defines ISIS LSP state information.";
    reference
      "1. https://github.com/openconfig/public/blob/master/release/models/isis/openconfig-isis-lsp.yang
       2. http://ops.openconfig.net/branches/models/master/docs/openconfig-isis.html
       3. https://github.com/openconfig/public/tree/master/release/models/isis";
    container lsp-states {
      description
        "Container of ISIS LSP state information.";
      list lsps {
        key "lsp-id pdu-type";
        description
          "LSP ID of the LSP, in the format, e.g. '640000000001-00-00'.
           LSP ID is consist of the System ID of a neighbor, the Pseudonode ID, and the LSP number of the LSPs.
           The last two bytes respectively represent Pseudonode ID and LSP number.
           A pseudonode is a logical representation of the LAN which is generated by a Designated Intermediate System (DIS)
           on a LAN segment. If one LSP is not fit by maximum LSP size then thats sent in another LSP with LSP number
           is incremented by 1.
           A router's learned LSP gets refreshed by 'remaining_lifetime'. Then the sequence number is incremented by 1.
           pdu-type can be either one of LEVEL_1 or LEVEL_2.
           A learned LSP is uniquely determined by LSP ID and pdu-type together.";

        leaf lsp-id {
          type leafref {
            path "../state/lsp-id";
          }
          description
            "A reference to the Link State PDU ID.";
        }
        leaf pdu-type {
          type leafref {
            path "../state/pdu-type";
          }
          description
            "A reference to the Link State PDU Type.";
        }

        container state {
          description
            "State parameters of Link State PDU.";

          leaf lsp-id {
            type otg-types:lsp-id;
            mandatory true;
            description
              "LSP ID of the LSP, e.g. '640000000001-00-00'.";
          }

          leaf pdu-type {
            type enumeration {
              enum LEVEL_1 {
                description "This enum describes ISIS level 1 PDU.";
              }
              enum LEVEL_2 {
                description "This enum describes ISIS level 2 PDU.";
              }
            }
            mandatory true;
            description
              "Link State PDU type.";
          }

          leaf remaining-lifetime {
            type uint16;
            units "seconds";
            mandatory true;
            description
              "Remaining lifetime in seconds before the LSP expiration.";
          }

          leaf sequence-number {
            type uint32;
            description
              "Sequence number of the LSP.";
          }

          leaf pdu-length {
            type uint16;
            mandatory true;
            description
              "Total length of the LSP.";
          }

          leaf-list flags {
            type enumeration {
               enum PARTITION_REPAIR {
                description
                  "When set, the originator supports partition
                  repair.";
              }
              enum ATTACHED_ERROR {
                description
                  "When set, the originator is attached to another
                  area using the referred metric.";
              }
              enum ATTACHED_EXPENSE {
                description
                  "When set, the originator is attached to another
                  area using the referred metric.";
              }
              enum ATTACHED_DELAY {
                description
                  "When set, the originator is attached to another
                  area using the referred metric.";
              }
              enum ATTACHED_DEFAULT {
                description
                  "When set, the originator is attached to another
                  area using the referred metric.";
              }
              enum OVERLOAD {
                description
                  "When set, the originator is overloaded, and must
                  be avoided in path calculation.";
              }
            }
            description
              "LSP Type-Block flags.";
          }

          leaf is-type {
            type uint8;
            mandatory true;
            description
              "IS Type - bits 1 and 2 indicate the type of Intermediate System.
                1 - ( i.e. bit 1 set) Level 1 Intermediate system.
                2 - Unused value.
                3 - (i.e. bits 1 and 2 set) Level 2 Intermediate system.";
          }
        }
        container tlvs {
          description
            "This container defines Link State PDU TLVs. When there are multiple occurences of a  specific TLV
            in a LSP, the data in the TLVs are combined and stored in the corresponding TLV container defined below.";

          container hostnames {
            description
              "This container describes list of Hostnames as defined in TLV 137.
              When there are multiple occurences of Hostname TLVs
              in a LSP, the data in the TLVs are combined and stored in the 'hostname' list.";

            container state {
              description
                "State parameters of ISIS TLV 137.";

              leaf-list hostname {
                type string;
                description
                  "Host name of the originating node.";

                reference
                  "RFC6233: IS-IS Registry Extension for Purges, RFC
                  5301: Dynamic Hostname Exchange Mechanism for IS-IS.
                  TLV 137";
              }
            }
          }

          container is-reachability {
            description
              "This container describes list of ISIS neighbors and
              attributes.
              This container describes list of IS-Reachability as defined in TLV 2.
              When there are multiple occurences of IS-Reachability TLVs
              in a LSP, the data in the TLVs are combined and stored in the 'neighbors' list.";

            reference
              "ISO 10589, Intermediate System to Intermediate System
              Intra- Domain Routeing Exchange Protocol for use in
              Conjunction with the Protocol for Providing the
              Connectionless-mode Network Service (ISO 8473),
              International Standard 10589: 2002, Second Edition,
              2002. TLV 2.";

            container neighbors {
              description
                "This container describes IS neighbors.";

              list neighbor {
                key "system-id";
                description
                  "IS reachability neighbor attributes.";

                leaf system-id {
                  type leafref {
                    path "../state/system-id";
                  }
                  description
                    "Reference to the system ID of the neighbor.";
                }
                container state {
                  description
                    "State parameters of IS standard neighbor.";

                  leaf system-id {
                    type otg-types:hex-string;
                    mandatory true;
                    description
                      "System-ID of IS neighbor, e.g. '640100010000'.";
                  }
                }
              }
            }
          }

          container extended-is-reachability {
            description
              "This container defines list of ISIS extended reachability
              neighbors and attributes.
              This container describes list of Extended-IS-Reachability as defined in TLV 22.
              When there are multiple occurences of Extended-IS-Reachability TLVs
              in a LSP, the data in the TLVs are combined and stored in the 'neighbors' list.";

            reference
              "RFC5305: IS-IS Extensions for Traffic Engineering. TLV
              22.";

            container neighbors {
              description
                "This container describes IS neighbors.";

              list neighbor {
                key "system-id";
                description
                  "IS reachability neighbor attributes.";

                leaf system-id {
                  type leafref {
                    path "../state/system-id";
                  }
                  description
                    "Reference to the system ID of the neighbor.";
                }

                uses isis-lsdb-neighbor;
              }
            }
          }

          container ipv4-internal-reachability {
            description
              "This container describes list of IPv4-Internal-Reachability as defined in TLV 128.
               This is advertised when the origin-type is set 'internal' in route range configuration.
               When there are multiple occurences of IPv4-Internal-Reachability TLVs in a LSP,
               the data in the TLVs are combined and stored in the 'prefixes' list.";

            reference
              "RFC1195: OSI ISIS for IP and Dual Environments. RFC5302:
              Domain-Wide Prefix Distribution with Two-Level IS-IS. TLV
              128";

            container prefixes {
              description
                "This container describes learned IPv4 prefixes.";

              list prefix {
                key "prefix";

                description
                  "IPv4 prefixes and internal reachability attributes.";

                leaf prefix {
                  type leafref {
                    path "../state/prefix";
                  }
                  description
                    "Reference to the IPv4 prefix";
                }
                uses ipv4-prefix-attributes-state;
              }
            }
          }

          container ipv4-external-reachability {
            description
              "This container describes list of IPv4-Internal-Reachability as defined in TLV 130.
               This is advertised when the origin-type is set 'external' in route range configuration.
               When there are multiple occurences of IPv4-external-Reachability TLVs in a LSP,
               the data in the TLVs are combined and stored in the 'prefixes' list.";

            reference
              "RFC1195: OSI ISIS for IP and Dual Environments. RFC5302:
              Domain-Wide Prefix Distribution with Two-Level IS-IS. TLV
              130";

            container prefixes {
              description
                "This container describes learned IPv4 prefixes.";

              list prefix {
                key "prefix";

                description
                  "IPv4 external prefixes and reachability attributes.";

                leaf prefix {
                  type leafref {
                    path "../state/prefix";
                  }
                  description
                    "Reference to the IPv4 prefix.";
                }

                uses ipv4-prefix-attributes-state;
              }
            }
          }


          container extended-ipv4-reachability {
            description
              "This container describes list of Extended-IPv4-Reachability as defined in TLV 135.
               It is advertised when the 'wide metric' is enabled.
               When there are multiple occurences of Extended-IPv4-Reachability TLVs in a LSP,
               the data in the TLVs are combined and stored in the 'prefixes' list.";

            reference
              "RFC5305: IS-IS Extensions for Traffic Engineering. TLV
              135";

            container prefixes {
              description
                "This container describes IS prefixes.";

              list prefix {
                key "prefix";

                description
                  "This list describes IPv4 extended prefixes and
                  attributes.";

                leaf prefix {
                  type leafref {
                    path "../state/prefix";
                  }
                  description
                    "Reference to the IPv4 prefix that the TLV describes
                    the attributes of.";
                }

                uses ipv4-prefix-extended-state;
              }
            }
          }

          container ipv6-reachability {
            description
              "This container describes list of IPv6 Reachability as defined in TLV 236.
               When there are multiple occurences of IPv6-Reachability TLVs in a LSP,
               the data in the TLVs are combined and stored in the 'prefixes' list.";

            reference
              "RFC5308: Routing IPv6 with IS-IS. TLV 236";

            container prefixes {
              description
                "This container describes learned IPv6 prefixes.";

              list prefix {
                key "prefix";

                description
                  "This list defines IPv6 extended prefix attributes.";

                leaf prefix {
                  type leafref {
                    path "../state/prefix";
                  }
                  description
                    "Reference to the IPv6 prefix that the TLV
                    corresponds to.";
                }

                uses ipv6-prefix-extended-state;
              }
            }
          }
          container router-capabilities {
            description
              "This list describes IS Router capabilities.";
            reference
              "RFC4971: Intermediate System to Intermediate System
              (IS-IS) Extensions for Advertising Router Information.
              TLV 242.";
            uses isis-lsdb-router-capabilities-state;
          }
        }
      }
    }
  }
  grouping isis-lsdb-neighbor {
    description
      "This grouping defines attributes of an ISIS standard
      neighbor.";

    container state {
      description
        "State parameters of IS standard neighbor.";

      leaf system-id {
        type otg-types:hex-string;
        mandatory true;
        description
          "System-ID of IS neighbor, e.g. '640100010000'.";
      }
      uses is-reachability-neighbor-adjacency-sids;
    }
  }

  grouping is-reachability-neighbor-adjacency-sids {
    description
      "This grouping defines the adjacency SIDs container when the
            sub-TLV type is 31.";
    list adjacency-sid {
      key "sid-instance";

      description
        "Adjacency Segment-IDs List. An IGP-Adjacency Segment is
        an IGP segment attached to a unidirectional adjacency or
        a set of unidirectional adjacencies. By default, an IGP-
        Adjacency Segment is local to the node which advertises
        it.";
      leaf sid-instance {
        type leafref {
          path "../state/sid-instance";
        }
        description
          "Reference to the value of the prefix SID. There may be array of prefix SIDs.
          https://datatracker.ietf.org/doc/html/rfc8667#name-adjacency-segment-identifie";
      }

      container state {
        description
          "State parameters of Adjacency-SID";
        leaf sid-instance {
          type uint32;
          description
            "A unique instance number for the instance for the Prefix-SID that may contain array of SIDs.";
        }

        leaf adjacency-type {
          type enumeration {
            enum ADJ-SID {
              description
                "Adjacency Segment Identifier (Adj-SID) Sub-TLV";
            }
            enum LAN-ADJ-SID  {
              description
                "LAN Adjacency Segment Identifier (LAN-Adj-SID) Sub-TLV";
            }
          }
          description
            "Adjacency-SID type: Adjacency SIDs(31) or LAN adjacency SID (32)";
        }
        leaf-list sids {
          type uint32;
          description
            "Reference to the values of one or more Adjacency-SIDs.";
        }
        leaf-list flags {
          type enumeration {
            enum ADDRESS_FAMILY {
              description
                "Address-family flag. When unset, the Adj-SID
                refers to an adjacency with outgoing IPv4
                encapsulation. If set then the Adj-SID refers to
                an adjacency with outgoing IPv6 encapsulation.";
            }
            enum BACKUP {
              description
                "Backup flag. When set, the Adj-SID refers to an
                adjacency being protected (e.g.: using IPFRR or
                MPLS-FRR).";
            }
            enum VALUE {
              description
                "Value flag. When set, the SID carries a value
                (instead of an index). By default the flag is
                SET.";
            }
            enum LOCAL {
              description
                "Local flag. When set, the value/index carried
                by the SID has local significance. By default
                the flag is SET.";
            }
            enum SET {
              description
                "Set flag. When set, the S-Flag indicates that
                the Adj-SID refers to a set of adjacencies.";
            }
            enum PERSISTENT {
              description
                "Persistent Flag. When set, the P-Flag indicates that the Adj-SID is persistently allocated, i.e.,
                the Adj-SID value remains consistent across router restart and/or interface flap.";
            }
          }
          description
            "Flags associated with Adj-Segment-ID.";
        }

        leaf weight {
          type uint8;
          description
            "Value that represents the weight of the Adj-SID for
            the purpose of load balancing.";
        }
      }
    }
    reference
      "draft-ietf-isis-segment-routing-extensions. sub-TLV 31:
      TLV 22, 222, 223, 141. ";
  }

  grouping isis-lsdb-common-metric-specification {
    description
      "Common definitions of the metric in IS-IS.";

    container default-metric {
      description
        "This container defines ISIS Default Metric.";

      container state {
        description
          "State parameters for default-metric.";

        leaf flags {
          type enumeration {
            enum INTERNAL {
              description
                "When set to zero, indicates internal metrics.";
            }
          }
          description
            "ISIS Default-Metric Flags.";
        }

        leaf metric {
          type uint8;
          description
            "ISIS default metric value. This is a metric understood by
            every Intermediate system in the domain. Each circuit
            shall have a positive  integral value assigned for this
            metric. The value may be associated with any  objective
            function of the circuit, but by convention is intended to
            measure the capacity of the circuit for handling traffic,
            for example, its throughput in  bits-per-second. Higher
            values indicate a lower capacity.";
        }
      }
    }
  }
  grouping ipv4-prefix-extended-state {
    description
      "This grouping defines attributes of an IPv4 extended prefix.";

    container state {
      description
        "State parameters of an IPv4 extended prefix.";
      uses ipv4-prefix-extended-params-state;
    }
  }

  grouping ipv4-prefix-extended-params-state {
    description
      "State parameters that relate to an IPv4 prefix";

    leaf prefix {
      type otg-types:ipv4-address;
      description
        "IPv4 prefix contained within extended reachability TLVs.";
    }

    leaf prefix-length {
      type uint32;
      description
        "The length of the IPv4 prefix.";
    }

    leaf metric {
      type uint32;
      description
        "ISIS wide metric.";
    }

    leaf redistribution-type {
      type enumeration {
        enum UP {
          description
            "Up (0)-used when a prefix is initially advertised within the ISIS L3 hierarchy,
            and for all other prefixes in L1 and L2 LSPs. (default).";
        }
        enum DOWN {
          description
            "Down (1)-used when an L1/L2 router advertises L2 prefixes in L1 LSPs.
            The prefixes are being advertised from a higher level (L2) down to a lower level (L1).";
        }
      }
      description
        "The up/down bit. Set if a prefix is advertised from a
        higher level to a lower level";
    }
    uses isis-lsdb-prefix-state;
    uses isis-lsdb-prefix-sid-state;
  }

  grouping ipv4-prefix-attributes-state {
   description
     "This group defines attributes of an IPv4 standard prefix.";

    container state {
     description
       "State parameters of IPv4 standard prefix.";
      leaf prefix {
        type otg-types:ipv4-address;
        description
          "IPv4 prefix contained within reachability TLVs.";
      }

      leaf prefix-length {
        type uint32;
        description
          "The length of the IPv4 prefix.";
      }

      leaf redistribution-type {
        type enumeration {
          enum UP {
            description
              "Up (0)-used when a prefix is initially advertised within the ISIS L3 hierarchy,
              and for all other prefixes in L1 and L2 LSPs. (default).";
          }
          enum DOWN {
            description
              "Down (1)-used when an L1/L2 router advertises L2 prefixes in L1 LSPs.
              The prefixes are being advertised from a higher level (L2) down to a lower level (L1).";
          }
        }
        description
          "The up/down bit. Set if a prefix is advertised from a
          higher level to a lower level";
      }

      leaf origin-type {
        type enumeration {
          enum INTERNAL {
            description
              "Internal-for intra-area routes, through Level 1 LSPs.";
          }
          enum EXTERNAL {
            description
              "External-for inter-area routes redistributed within L1, through Level 1 LSPs.";
          }
        }
        description
          "The origin of the advertised route-internal or external to the ISIS area.";
      }

      leaf default-metric {
        type uint8;
        description
          "ISIS default metric value.";
      }
    }
  }

  grouping isis-lsdb-prefix-sid-state {
    description
      "This grouping defines ISIS Prefix SID.";
    list prefix-sid {
      key "sid-instance";
      description
        "Prefix Segment-ID list. IGP-Prefix Segment is an IGP segment
        attached to an IGP prefix. An IGP-Prefix Segment is global
        (unless explicitly advertised otherwise) within the SR/IGP
        domain.";

      leaf sid-instance {
        type leafref {
          path "../state/sid-instance";
        }
        description
          "Reference to the value of the prefix SID. There may be array of prefix SIDs.
          https://datatracker.ietf.org/doc/html/rfc8667#name-prefix-segment-identifier-p";
      }

      container state {
        description
          "State parameters for Prefix-SID.";
        leaf sid-instance {
          type uint32;
          description
            "A unique instance number for the instance for the Prefix-SID that may contain array of SIDs.";
        }
        leaf-list sids {
          type uint32;
          description
            "IGP one more SID values.";
        }

        leaf-list flags {
          type enumeration {
            enum READVERTISEMENT {
              description
                "Readvertisment flag. When set, the prefix to which
                this Prefix-SID is attached, has been propagated by
                the router either from another level or from
                redistribution.";
            }
            enum NODE {
              description
                "Node flag. When set, the Prefix-SID refers to the
                router identified by the prefix. Typically, the
                N-Flag is set on Prefix-SIDs attached to a router
                loopback address.";
            }
            enum NO_PHP {
              description
                "Penultimate-Hop-Popping flag. When set, then the
                penultimate hop MUST NOT pop the Prefix-SID before
                delivering the packet to the node that advertised
                the Prefix-SID.";
            }
            enum EXPLICIT_NULL {
              description
                "Explicit-Null flag. When set, any upstream neighbor
                of the Prefix-SID originator MUST replace the
                Prefix-SID with a Prefix-SID having an Explicit-NULL
                value (0 for IPv4 and 2 for IPv6) before forwarding
                the packet.";
            }
            enum VALUE {
              description
                "Value flag. When set, the Prefix-SID carries a
                value (instead of an index). By default the flag is
                UNSET.";
            }
            enum LOCAL {
              description
                "Local flag. When set, the value/index carried by
                the Prefix-SID has local significance. By default
                the flag is UNSET.";
            }
          }
          description
            "Flags associated with Prefix Segment-ID.";
        }

        leaf algorithm {
          type uint8;
          description
            "Prefix-SID algorithm to be used for path computation.";
        }
      }
    }
  }

  grouping isis-counters {
    description
      "Level counters of the ISIS router.";

    leaf sessions-up {
      type otg-types:counter64;
      description
        "The total number of sessions that are fully up.";
    }

    leaf sessions-flap {
      type otg-types:counter64;
      description
        "The total number of sessions flap.";
    }

    leaf database-size {
      type otg-types:counter64;
      description
        "The total number of link stOTG updOTGs (LSPs) in the LSP
        databases.";
    }

    leaf out-bcast-hellos {
      type otg-types:counter64;
      description
        "The total number of broadcast HELLO messages sent.";
    }

    leaf in-bcast-hellos {
      type otg-types:counter64;
      description
        "The total number of broacast HELLO messages received.";
    }

    leaf out-p2p-hellos {
      type otg-types:counter64;
      description
        "The total number of point to point (P2P) HELLO messages
        sent.";
    }

    leaf in-p2p-hellos {
      type otg-types:counter64;
      description
        "The total number of point to point (P2P) HELLO messages
        received.";
    }

    leaf out-psnp {
      type otg-types:counter64;
      description
        "The total number of partial sequence number packet (PSNPs)
        messages sent.";
    }

    leaf in-psnp {
      type otg-types:counter64;
      description
        "The total number of partial sequence number packet (PSNPs)
        messages received.";
    }

    leaf out-csnp {
      type otg-types:counter64;
      description
        "The total number of complete sequence number packet (CSNPs)
        messages sent.";
    }

    leaf in-csnp {
      type otg-types:counter64;
      description
        "The total number of complete sequence number packet (CSNPs)
        messages received.";
    }

    leaf out-lsp {
      type otg-types:counter64;
      description
        "The total number of link state protocol data units (LSPs)
        sent.";
    }

    leaf in-lsp {
      type otg-types:counter64;
      description
        "The total number of link state protocol data units (LSPs)
        received.";
    }
  }

  grouping isis-lsdb-tlv-type-state {
    description
      "Per-subTLV type operational state parameters for ISIS.";

    leaf type {
      type uint8;
      mandatory true;
      description
        "The type of TLV being described. The type of TLV is
        expressed as a canonical name.";
    }
  }

  grouping isis-lsdb-common-extisreach-neighbors {
    description
      "Common structure for the Extended IS Reachability and IS
      Reachability Neighbour attributes.";

    container neighbors {
      description
        "This container describes IS neighbors.";

      list neighbor {
        key "system-id";
        description
          "This list describes ISIS extended neighbors and
          reachability attributes.";

        leaf system-id {
          type leafref {
            path "../state/system-id";
          }
          description
            "Reference to the neighboring system's system ID.";
        }

        container state {
          description
            "State parameters corresponding to the extended
            neighbour.";

          leaf system-id {
            type otg-types:hex-string;
            description
              "System-id of the neighbor.";
          }
        }
      }
    }
  }

  grouping isis-lsdb-subtlv-type-state {
    description
      "Per-subTLV type operational state parameters for ISIS.";

    leaf type {
      type uint8;
      mandatory true;
      description
        "The type of subTLV being described. The type of subTLV is
        expressed as a canonical name.";
    }
  }

  grouping ipv6-prefix-extended-state {
    description
      "State parameters relating to an IPv6 prefix.";

    container state {
      description
        "State parameters of IPv6 prefix attributes";

      uses ipv6-prefix-extended-params-state;
      uses isis-lsdb-prefix-state;
    }
  }

  grouping ipv6-prefix-extended-params-state {
    description
      "Common parameters of an IPv6 extended prefix.";

    leaf prefix {
      type otg-types:ipv6-address;
      description
        "IPv6 prefix contained within extended reachability TLVs.";
    }

    leaf prefix-length {
      type uint32;
      description
        "The length of the IPv6 prefix.";
    }

    leaf redistribution-type {
      type enumeration {
        enum UP {
          description
            "Up (0)-used when a prefix is initially advertised within the ISIS L3 hierarchy,
            and for all other prefixes in L1 and L2 LSPs. (default).";
        }
        enum DOWN {
          description
            "Down (1)-used when an L1/L2 router advertises L2 prefixes in L1 LSPs.
            The prefixes are being advertised from a higher level (L2) down to a lower level (L1).";
        }
      }
      description
        "The up/down bit. Set if a prefix is advertised from a
        higher level to a lower level";
    }

    leaf origin-type {
      type enumeration {
        enum INTERNAL {
          description
            "Internal-for intra-area routes, through Level 1 LSPs.";
        }
        enum EXTERNAL {
          description
            "External-for inter-area routes redistributed within L1, through Level 1 LSPs.";
        }
      }
      description
        "The origin of the advertised route-internal or external to the ISIS area.";
    }

    leaf metric {
      type uint32;
      description
        "ISIS wide metric value.";
    }
    uses isis-lsdb-prefix-sid-state;
  }

  grouping isis-lsdb-prefix-state {
    description
      "This grouping defines prefix reachability.";

    container prefix-attributes {
      description
        "This container defines sub-TLV 4.";
      leaf-list flags {
        type enumeration {
          enum EXTERNAL_FLAG {
            description
              "External prefix flag. Set if the prefix has been
              redistributed from another protocol. This includes
              the case where multiple virtual routers are
              supported and the source of the redistributed prefix
              is another IS-IS instance.";
          }
          enum READVERTISEMENT_FLAG {
            description
              "Readvertisement flag. Set when the prefix has been
              leaked from one level to another (upwards or
              downwards).";
          }
          enum NODE_FLAG {
            description
              "Node flag. Set when the prefix identifies the
              advertising router, i.e., the prefix is a host
              prefix advertising  a globally reachable address
              typically associated with a loopback address.";
          }
        }
        description
          "Additional prefix reachability flags.";

        reference
          "RFC7794: IS-IS Prefix Attributes for Extended IPv4 and
          IPv6 Reachability. sub-TLV 4.";
      }
    }
  }

  grouping isis-lsdb-router-capabilities-state {
    description
      "Only include the router capability TLV when the TLV is
      type 242.";
    list capability {
      key "instance-number";
      description
        "This list describes IS Router capabilities.";
      leaf instance-number {
        type leafref {
          path "../state/instance-number";
        }
        description
          "Reference to the instance number of the router
          capability TLV.";
      }
      container state {
        description
          "State parameters of TLV 242.";
        leaf instance-number {
          type uint32;
          description
            "A unique instance number for the instance of the
            router capabilities TLV. The instance number should
            be autogenerated by the producer of the data and may
            be renumbered if the entire LSP contents are
            replaced in subsequent advertisements.";
        }

        leaf router-id {
          type otg-types:ipv4-address;
          description
            "IPv4 router-id.";
        }
        leaf-list flags {
          type enumeration {
            enum FLOOD {
              description
                "When the S bit is set(1), the IS - IS Router
                CAPABILITY TLV MUST be flooded across the entire
                routing domain. When the S bit is not set(0),
                the TLV MUST NOT be leaked between levels . This
                bit MUST NOT be altered during the TLV
                leaking.";
            }
            enum DOWN {
              description
                  "When the IS-IS Router CAPABILITY TLV is leaked
                  from level - 2 to level-1, the Down bit MUST be
                  set. Otherwise, this bit MUST be clear. IS - IS
                  Router capability TLVs with the Down bit set
                  MUST NOT be leaked from level - 1 to level-2.
                  This is to prevent TLV looping.";
              }
            }
            description
              "Router capability flags.";
        }
        leaf-list algorithms {
          type uint32;
          description
            "The Segment Routing algorithm that is
            described by the TLV.";
        }
        container segment-routing-capability {
          description
            "This container defines SR Capability sub-TLV 2.";
          container state {
            description
              "State parameters of IS SR Router Capability";

            leaf-list flags {
              type enumeration {
                enum IPV4_MPLS {
                  description
                    "When set, the router is capable of
                    processing SR MPLS encapsulated IPv4
                    packets on all interfaces.";
                }
                enum IPV6_MPLS {
                    description
                      "When set, the router is capable of
                      processing SR MPLS encapsulated IPv6
                      packets on all interfaces.";
                }
              }
              description
                "Segment Routing Capability Flags.";
            }
            list srgb-descriptor {
              key "range";
              description
                "Descriptor entry within the SR capabilty
                sub-TLV";

              leaf range {
                type leafref {
                  path "../state/range";
                }
                description
                  "Reference to unique SRGB Descriptor.";
              }

              container state {
                description
                  "State parameters of the SR range";

                  leaf range {
                    type uint32;
                    description
                      "Number of SRGB elements. The range
                      value MUST be greater than 0.";
                  }

                  leaf starting-level {
                    type uint32;
                    description
                      "The first value of the SRGB when
                      expressed as an MPLS label.";
                  }
              }
            }
          }
        }
        container sr-local-block-ranges {
          description
            "This container defines SR Local Block (SRLB) sub-TLV contains the range of labels the
             node has reserved for Local SIDs";
          container state {
            description
              "State parameters of IS SR Local Block (SRLB)";
            list srlbs-descriptor {
              key "range";
              description
                "Descriptor entry within the SR capabilty
                sub-TLV";

              leaf range {
                type leafref {
                  path "../state/range";
                }
                description
                  "Reference to unique SRLB Descriptor.";
              }

              container state {
                description
                  "State parameters of the SRLB range";

                  leaf range {
                    type uint32;
                    description
                      "Number of SRLB elements. The range
                      value MUST be greater than 0.";
                  }

                  leaf starting-level {
                    type uint32;
                    description
                      "The first value of the SRLB when
                      expressed as an MPLS label.";
                  }
              }
            }
          }
        }

      }
    }
  }

   grouping adjacency-states {
    description
      "This grouping defines ISIS IIH state information.";
    container state {
      description
        "Container of ISIS IIH state information.";
      list adjacency {
        key "neighbor-system-id interface-name";
        description
          "System ID of a neighbor and Interface name on which neighbor is established.";

        leaf neighbor-system-id {
          type leafref {
            path "../state/neighbor-system-id";
          }
          description
            "A reference to the neighbor system id.";
        }
        leaf interface-name {
          type leafref {
            path "../state/interface-name";
          }
          description
            "A reference to to the name of the ISIS interface as provided during set_config.";
        }

        container state {
          description
            "State parameters of IIH adjacency.";

          leaf neighbor-system-id {
            type otg-types:hex-string;
            mandatory true;
            description
              "Neighbor System ID e.g. '650000000001'.";
          }

          leaf interface-name {
            type string;
            mandatory true;
            description
              "ISIS Interface name as defined in set_config";
          }
          uses iih-local-state;
          uses iih-neighbor-state;
        }
      }
    }
  }

  grouping iih-local-state {
    description
      "Information for a Local Adjacency.";
    container local-state {
      description
        "Local State parameter.";
      container state {
        description
          "State parameters of IIH Adjacency.";
        leaf level-type {
          type enumeration {
            enum LEVEL_1 {
              description "This enum describes ISIS level 1 IIH.";
            }
            enum LEVEL_2 {
              description "This enum describes ISIS level 2 IIH.";
            }
            enum LEVEL_1_2 {
              description "This enum describes ISIS level 1-2 IIH.";
            }
          }
          description
            "IIH Level type.";
        }
        leaf hold-timer {
          type uint32;
          description
            "Hold timer being sent in the IIH PDU.";
        }
        uses iih-local-restarting-status;
      }
    }
  }

  grouping iih-neighbor-state {
    description
      "Information for a Neighbor Adjacency.";
    container neighbor-state {
      description
        "Neighbor Adjacency .";
      container state {
        description
          "State parameters of IIH Neighbor Adjacency.";
         leaf level-type {
          type enumeration {
            enum LEVEL_1 {
              description "This enum describes ISIS level 1 IIH.";
            }
            enum LEVEL_2 {
              description "This enum describes ISIS level 2 IIH.";
            }
            enum LEVEL_1_2 {
              description "This enum describes ISIS level 1-2 IIH.";
            }
          }
          description
            "IIH Level type.";
        }
        leaf hold-timer {
          type uint32;
          description
            "Hold timer being sent in the IIH PDU.";
        }
        uses iih-neigh-restarting-status;
        container tlvs {
          description
            "This contains the list of TLVs present in a IIH PDU received from a neighbor IS-IS router.";
          container restart_tlv {
            description
              "Container of Restart TLV in IIH PDU. Reference: https://datatracker.ietf.org/doc/html/rfc8706#name-restart-tlv.";
            container state {
              description
                "State parameters of ISIS TLV 137.";
              leaf-list flags {
                type enumeration {
                  enum RR_BIT {
                    description
                      "Restart Request bit.";
                  }
                  enum RA_BIT {
                    description
                      "Restart Acknowledgement.";
                  }
                  enum SA_BIT {
                    description
                      "Suppress Adjacency Advertisement.";
                  }
                  enum PR_BIT {
                    description
                      "Restart Planned.";
                  }
                  enum PA_BIT {
                    description
                      "Planned Pestart Acknowledgement.";
                  }
                }
                description
                  "Flags associated with Restarting TLV";
              }

              leaf remaining-time {
                type uint32;
                description
                  "Remaining Holding Time (in seconds).";
              }
              leaf restarting-neighbor-id {
                type otg-types:hex-string;
                description
                  "Restarting Neighbor's System ID in hex format without '0x' at the beginning. e.g. '640000000001'.";
              }
            }
          }
        }
      }
    }
  }

   grouping iih-local-restarting-status {
    description
      "This contains the Restarting/Starting/Running state of this router.";
    container local-restarting-status {
      description
        "Container for Restarting Status.";
      container state {
        description
          "State for Restarting Status.";
        leaf current-state {
          type enumeration {
            enum RUNNING {
              description "Running state when Restarting Tlv is not present or Restarting Tlv has been sent with SA or RR bits unset.";
            }
            enum RESTARTING {
              description "Restarting state when Restarting Tlv has been sent with RR bits set.";
            }
            enum STARTING {
              description "Starting state when Restarting Tlv has been sent with SA bit set.";
            }
          }
          description
            "Restart State of this Router.";
        }
        uses iih-local-last-restarting-attempt-status;
      }
    }
  }

  grouping iih-neigh-restarting-status {
    description
      "This contains the Restarting/Starting/Running state of a neighbor router.";
    container neigh-restarting-status {
      description
        "Container for Restarting Status.";
      container state {
        description
          "State for Restarting Status.";
        leaf current-state {
          type enumeration {
            enum RUNNING {
              description "Running state when Restarting Tlv is not present or Restarting Tlv has been sent with SA or RR bits unset.";
            }
            enum RESTARTING {
              description "Restarting state when Restarting Tlv has been sent with RR bits set.";
            }
            enum STARTING {
              description "Starting state when Restarting Tlv has been sent with SA bit set.";
            }
          }
          description
            "Restart State of the Neigbhor Router.";
        }
        uses iih-neigh-last-restarting-attempt-status;
      }
    }
  }

  grouping iih-local-last-restarting-attempt-status {
     description
      "This object contains the status of the last attempted Graceful Restart status of this router.";
    container local-last-restarting-attempt-status {
      description
        "Container for Restarting Attempt Status.";
      container state {
        description
          "State of Restarting Attempt Status.";
        leaf local-last-restarting-attempt-status-type {
          type enumeration {
            enum SUCCEEDED {
              description
                "This enum describes if the last Graceful Restart attempt initiated by the local ISIS Router was successful.";
            }
            enum FAILED {
              description
                "The last Graceful Restart attempt initiated by the local ISIS router was unsuccessful.";
            }
            enum INPROGRESS {
              description
                "The last Graceful Restart attempt initiated by the local ISIS router is in progress.";
            }
            enum UNAVAILABLE {
              description
                "Graceful Restart has never been initiated by the local ISIS router.";
            }
          }
          description
            "The status of the last attempted Graceful Restart by the local ISIS router.";
        }
        uses iih-local-last-restarting-attempt-succeeded;
        uses iih-local-last-restarting-attempt-failed;
      }
    }
  }

  grouping iih-neigh-last-restarting-attempt-status {
     description
      "This object contains the status of the last attempted Graceful Restart status of an ISIS neighbor.";
    container neigh-last-restarting-attempt-status {
      description
        "Container for Restarting Attempt Status.";
      container state {
        description
          "State of Restarting Attempt Status.";
        leaf neigh-last-restarting-attempt-status-type {
          type enumeration {
            enum SUCCEEDED {
              description
                "The last Graceful Restart attempt initiated by the neighboring ISIS router was successful.";
            }
            enum FAILED {
              description
                "The last Graceful Status of this neighbor is unsuccessful.";
            }
            enum INPROGRESS {
              description
                "The last Graceful Restart status of this neighbor is in progress.";
            }
            enum UNAVAILABLE {
              description
                "The last Graceful Restart status of this neighbor is not initiated.";
            }
          }
          description
            "The result type of Restarting Attempt Status of this neighbor";
        }
        uses iih-neigh-last-restarting-attempt-succeeded;
        uses iih-neigh-last-restarting-attempt-failed;
      }
    }
  }

  grouping iih-local-last-restarting-attempt-succeeded {
     description
      "This container contains details about the successful status of the last Graceful Restart initiated by this router.";
    container local-last-restarting-attempt-succeeded {
      description
        "Container for for additional information related to the last Graceful Restart attempt initiated by the local ISIS Router if it succeeded.";
      container state {
        description
          "State of Restarting Attempt Status.";
         leaf local-lsdb-syncup-time {
          type uint32;
          description
            "The time (in seconds) is taken to synchronize the L1 and L2 LSDB by this Restarting router.
            By this time, the CSNP list is cleared and all LSPs are collected by the neighbor(s)";
        }
        leaf local-adjacency-bring-up-time {
          type uint32;
          description
            "The time (in seconds) is measured from when the Restart TLV with RR bit set is sent
             in an IIH PDU upto the time when Restart TLV is sent with RR bit unset.";
        }
      }
    }
  }

  grouping iih-local-last-restarting-attempt-failed {
     description
      "This container contains additional information related to the last Graceful Restart attempt initiated by the local ISIS Router if it failed.";
    container local-last-restarting-attempt-failed {
      description
        "Container for Last Restarting Attempt that was succeeded.";
      container state {
        description
          "State Information of failed restart";
         leaf reason {
          type string;
          description
            "Failure reason of last Graceful Restart.";
        }
      }
    }
  }

 grouping iih-neigh-last-restarting-attempt-succeeded {
     description
      "This container contains additional information related to the last Graceful Restart attempt initiated by the neighboring ISIS Router if it succeeded.";
    container neigh-last-restarting-attempt-succeeded {
      description
        "Container for Last Restarting Attempt that was succeeded.";
      container state {
        description
          "State of Restarting Attempt Status.";
        leaf neigh-adjacency-bring-up-time {
          type uint32;
          description
            "The time (in second) is measured from when the Restart TLV with RR bit set in a IIH PDU is received up to the time when it receives
            the Restart TLV with RR bit and SA bit unset in a IIH PDU from the Neighbor Router.";
        }
      }
    }
  }

  grouping iih-neigh-last-restarting-attempt-failed {
     description
      "This container contains additional information related to the last Graceful Restart attempt initiated by the neighboring ISIS Router if it failed.";
    container neigh-last-restarting-attempt-failed {
      description
        "Container for Last Restarting Attempt that was succeeded.";
      container state {
        description
          "State Information of a failed restart";
         leaf reason {
          type string;
          description
            "Failure reason of last Graceful Restart.";
        }
      }
    }
  }

  uses isis-top;
}
